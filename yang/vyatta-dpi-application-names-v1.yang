module vyatta-dpi-application-names-v1 {
	namespace "urn:vyatta.com:mgmt:vyatta-dpi-application-names:1";
	prefix vyatta-dpi-application-names-v1;

	import vyatta-opd-extensions-v1 {
		prefix opd;
	}

	organization "AT&T Inc.";
	contact	"AT&T
		 Postal: 208 S. Akard Street
		         Dallas, TX 75202, USA
		 Web: www.att.com";

	description
		"Copyright (c) 2017-2020, AT&T Intellectual Property
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 DPI application names";

	revision 2020-05-12 {
		description "Obsoleted application-names, relaxed-application-names,
		             and all the enum values.";
	}
	revision 2019-12-11 {
		description "Corrected contact address.
			     Added BSD-3-Clause license.
			     Corrected some typos.";
	}
	revision 2018-11-20 {
		description "Updated to 1.410";
	}
	revision 2018-03-31 {
		description "Updated to 1.380";
	}
	revision 2018-02-01 {
		description "360 + 370 Update:
			     - added/obsoleted multiple applications.
			     - improvements and corrections to existing
			       opd:help strings throughout.";
	}
	revision 2017-10-31 {
		description "Obsoleted deprecated applications
			     and all unassigned_ip_prot_nnn";
	}
	revision 2017-09-01 {
		description "Initial version";
	}

	typedef application-names {
		status obsolete;
		type enumeration {
			enum "01net" {
				opd:help "01net website, a French high-tech news site";
				status obsolete;
			}

			enum "050plus" {
				opd:help "050 plus is a Japanese embedded smartphone application dedicated to audio-conferencing";
				status obsolete;
			}

			enum "0zz0" {
				opd:help "0zz0 is an online solution to store, send and share files";
				status obsolete;
			}

			enum "10050net" {
				opd:help "China Railcom group web portal";
				status obsolete;
			}

			enum "10086cn" {
				opd:help "This classifies the HTTP traffic to the host 10086.cn";
				status obsolete;
			}

			enum "104com" {
				opd:help "Website dedicated to job research";
				status obsolete;
			}

			enum "1111tw" {
				opd:help "Website dedicated to job research in Taiwan";
				status obsolete;
			}

			enum "114la" {
				opd:help "Chinese web portal operated by YLMF Computer Technology Co";
				status obsolete;
			}

			enum "115com" {
				opd:help "Chinese cloud storing system of the 115 website";
				status obsolete;
			}

			enum "118114cn" {
				opd:help "Chinese booking and reservation portal";
				status obsolete;
			}

			enum "11st" {
				opd:help "Korean shopping website 11st";
				status obsolete;
			}

			enum "123people" {
				opd:help "(Deprecated) This classifies the HTTP traffic to the host 123people.com";
				status obsolete;
			}

			enum "1337x" {
				opd:help "BitTorrent tracker search engine";
				status obsolete;
			}

			enum "139mail" {
				opd:help "139mail is a Chinese webmail powered by China Mobile";
				status obsolete;
			}

			enum "15min" {
				opd:help "Lithuanian news portal";
				status obsolete;
			}

			enum "163com" {
				opd:help "Chinese web portal 163";
				status obsolete;
			}

			enum "17173com" {
				opd:help "Website distributing Chinese games";
				status obsolete;
			}

			enum "17u" {
				opd:help "Chinese online travel booking website";
				status obsolete;
			}

			enum "20min" {
				opd:help "Swiss news portal";
				status obsolete;
			}

			enum "24h" {
				opd:help "Vietnamese news portal";
				status obsolete;
			}

			enum "24ora" {
				opd:help "Aruban news portal";
				status obsolete;
			}

			enum "24sata" {
				opd:help "Croatian news portal";
				status obsolete;
			}

			enum "24ur" {
				opd:help "Slovenian news portal";
				status obsolete;
			}

			enum "2ch" {
				opd:help "Japanese adult videos website";
				status obsolete;
			}

			enum "2shared" {
				opd:help "2shared is an online space for sharing and storage";
				status obsolete;
			}

			enum "3366_com" {
				opd:help "3366.com is an online secure flash game website";
				status obsolete;
			}

			enum "360buy" {
				opd:help "(Deprecated) This classified the HTTP traffic to the host 360buy.com";
				status obsolete;
			}

			enum "360cn" {
				opd:help "Chinese web portal featuring a search engine and security-oriented software services";
				status obsolete;
			}

			enum "3gpp_li" {
				opd:help "3gpp_li is a protocol which form a standard for telecoms operators and networks operators";
				status obsolete;
			}

			enum "3pc" {
				opd:help "The 3pc protocol (Third Party Connect Protocol) is found over the IP layer (IANA protocol number: 34)";
				status obsolete;
			}

			enum "4399com" {
				opd:help "Chinese game platform 4399";
				status obsolete;
			}

			enum "4chan" {
				opd:help "4chan is an image-based bulletin board where people can share and comment on images";
				status obsolete;
			}

			enum "4shared" {
				opd:help "4shared is an online space for sharing and storage";
				status obsolete;
			}

			enum "4tube" {
				opd:help "4tube is a free pornographic video sharing website, similar in concept, but unrelated to YouTube";
				status obsolete;
			}

			enum "51_com" {
				opd:help "Provide social networking applications, IM, music, photo albums";
				status obsolete;
			}

			enum "51_com_bbs" {
				opd:help "BBS, Forum";
				status obsolete;
			}

			enum "51_com_music" {
				opd:help "Music streaming";
				status obsolete;
			}

			enum "51_com_posting" {
				opd:help "Collaboration website";
				status obsolete;
			}

			enum "51job" {
				opd:help "Search engine for job-seekers in China";
				status obsolete;
			}

			enum "51la" {
				opd:help "Chinese website that provides website statistics to its users";
				status obsolete;
			}

			enum "56com" {
				opd:help "Chinese video-hosting website";
				status obsolete;
			}

			enum "58com" {
				opd:help "Chinese classified ads website";
				status obsolete;
			}

			enum "591tw" {
				opd:help "Taiwanese real estate website";
				status obsolete;
			}

			enum "5pmweb" {
				opd:help "5pmweb is a web-based project and task management software for teams";
				status obsolete;
			}

			enum "6alabat" {
				opd:help "Kuwaitian online restaurant ordering website";
				status obsolete;
			}

			enum "6play" {
				opd:help "French mobile application providing live and replay television programs of the M6 media group";
				status obsolete;
			}

			enum "7k7k" {
				opd:help "Chinese game portal";
				status obsolete;
			}

			enum "802_11" {
				opd:help "The 802.11 protocol is used to carry data (at MAC level) on IEEE 802.11 Wireless Local Area Networks";
				status obsolete;
			}

			enum "8tracks" {
				opd:help "Internet radio and social networking website based on user-made playlists streaming";
				status obsolete;
			}

			enum "91com" {
				opd:help "The TQ game entertainment portal";
				status obsolete;
			}

			enum "999_md" {
				opd:help "Moldavian classified ads";
				status obsolete;
			}

			enum "99acres" {
				opd:help "99Acres is a popular Real Estate portal in India";
				status obsolete;
			}

			enum "9game" {
				opd:help "Chinese game distribution platform";
				status obsolete;
			}

			enum "a_dakar" {
				opd:help "Senegalese news portal";
				status obsolete;
			}

			enum "aajtak" {
				opd:help "AAJTAK is a popular site in India used for streaming videos";
				status obsolete;
			}

			enum "aastocks" {
				opd:help "Chinese financial services and stock market website";
				status obsolete;
			}

			enum "abc" {
				opd:help "ABC is a BitTorrent client based on BitTornado";
				status obsolete;
			}

			enum "abc_au" {
				opd:help "News streaming website of Australian Broadcasting Corporation";
				status obsolete;
			}

			enum "abc_news" {
				opd:help "Paraguayan news portal";
				status obsolete;
			}

			enum "abcnews" {
				opd:help "ABC News is one of the major news outlets in the United States";
				status obsolete;
			}

			enum "abidjan" {
				opd:help "Cote d'Ivoire news portal";
				status obsolete;
			}

			enum "abola" {
				opd:help "Portuguese sports news portal";
				status obsolete;
			}

			enum "about" {
				opd:help "(Deprecated) Commercial news website owned by the New York Times Company";
				status obsolete;
			}

			enum "abs_cbn" {
				opd:help "Philippino TV channel website";
				status obsolete;
			}

			enum "abs_cbnnews" {
				opd:help "Filipino news portal";
				status obsolete;
			}

			enum "abv" {
				opd:help "Bulgarian webmail";
				status obsolete;
			}

			enum "ac_reunion" {
				opd:help "Ministerial web portal of La Reunion island";
				status obsolete;
			}

			enum "acbar" {
				opd:help "Afghan NGO information and activities related website";
				status obsolete;
			}

			enum "accuweather" {
				opd:help "Company which provides weather reports for people and companies worldwide";
				status obsolete;
			}

			enum "aceproject" {
				opd:help "AceProject is a free collaboration-oriented project management software with features such as Gantt charts, time tracking and expense tracking";
				status obsolete;
			}

			enum "acer" {
				opd:help "Acer is an electronics and hardware company based in New Taipei City, Taiwan";
				status obsolete;
			}

			enum "acrobat" {
				opd:help "Cloud services of Adobe, the American software company";
				status obsolete;
			}

			enum "acse" {
				opd:help "ISO 8650-1/X.227 OSI Association Control SErvice (ACSE)";
				status obsolete;
			}

			enum "activenet" {
				opd:help "The activenet protocol (Active Networks) is found over the IP layer (IANA protocol number: 107)";
				status obsolete;
			}

			enum "activesync" {
				opd:help "Exchange ActiveSync (EAS) is a mobile data synchronization technology and protocol developed by Microsoft, originally released in 1996";
				status obsolete;
			}

			enum "actuniger" {
				opd:help "News web portal in Niger about politics, economy, sports, etc";
				status obsolete;
			}

			enum "adaderana" {
				opd:help "SriLankan news portal";
				status obsolete;
			}

			enum "adc" {
				opd:help "ADC is a peer-to-peer protocol widely used in Direct Connect networks";
				status obsolete;
			}

			enum "adcash" {
				opd:help "Adcash is an international Ad network providing Internet publishers";
				status obsolete;
			}

			enum "adcolony" {
				opd:help "AdColony is a mobile video advertising platform";
				status obsolete;
			}

			enum "addictinggames" {
				opd:help "Addicting Games websites, operated by the American company Defy Media";
				status obsolete;
			}

			enum "addthis" {
				opd:help "AddThis is a social bookmarking service that can be integrated into a website with the use of a web widget";
				status obsolete;
			}

			enum "adf" {
				opd:help "Advertising platform providing an API to redirect websites using paid links";
				status obsolete;
			}

			enum "adform" {
				opd:help "Adform is a global digital media advertising technology company";
				status obsolete;
			}

			enum "adjara" {
				opd:help "Global internet portal in Georgia";
				status obsolete;
			}

			enum "adjaranet" {
				opd:help "Pirate Video Direct DownLoad website from Georgia, featuring top series and movies";
				status obsolete;
			}

			enum "adjust" {
				opd:help "Adjust is a business intelligence platform for mobile app marketers";
				status obsolete;
			}

			enum "adk2" {
				opd:help "Adk2 enables ad networks to maximize their revenue";
				status obsolete;
			}

			enum "adnetworkperformance" {
				opd:help "Tracking and advertisement servers in Algeria likely related to malware programs";
				status obsolete;
			}

			enum "adnstream" {
				opd:help "ADNstream is a Spanish streaming platform";
				status obsolete;
			}

			enum "adobe" {
				opd:help "Adobe Systems is a computer software company";
				status obsolete;
			}

			enum "adobe_connect" {
				opd:help "Adobe Connect is a web communication system for training, marketing, conferences and online collaboration";
				status obsolete;
			}

			enum "adobe_meeting_rc" {
				opd:help "Websites of the Adobe Connect software";
				status obsolete;
			}

			enum "adobe_online_office" {
				opd:help "(Deprecated) Online collaborative office";
				status obsolete;
			}

			enum "adobe_update" {
				opd:help "The Adobe Update Manager is a program which maintains up-to-date versions of Adobe Acrobat Reader software";
				status obsolete;
			}

			enum "adp" {
				opd:help "Provider of human resources management software";
				status obsolete;
			}

			enum "adplex_media" {
				opd:help "Advertising network traffic by Adplex Media";
				status obsolete;
			}

			enum "adrive" {
				opd:help "ADrive is a cloud storing system operated by an American company, ADrive LLC";
				status obsolete;
			}

			enum "adsafeprotected" {
				opd:help "Ad Safe Protected is a service provided by Integral Ad Science, used to determine if ad views and clicks are high-quality and valid";
				status obsolete;
			}

			enum "adserverplus" {
				opd:help "Online advertisement";
				status obsolete;
			}

			enum "adtech" {
				opd:help "Integrated ad serving solutions enabling web publishers, ad networks, agencies and advertisers to manage, serve and report on their online advertising campaigns";
				status obsolete;
			}

			enum "adultadworld" {
				opd:help "Advertising network for adult content websites";
				status obsolete;
			}

			enum "adultfriendfinder" {
				opd:help "Social and dating network for adults";
				status obsolete;
			}

			enum "advection" {
				opd:help "Advection.NET is a video delivery network with live and on-demand paid media features";
				status obsolete;
			}

			enum "adventori" {
				opd:help "ADventori is a data-driven adserver";
				status obsolete;
			}

			enum "advertising_com" {
				opd:help "Advertising.com is a massive premium, cross-screen network with several million global unique visitors, programmatic buying, a proprietary DSP, and network-exclusive access to AOL inventory";
				status obsolete;
			}

			enum "advogato" {
				opd:help "Social network for free software editors";
				status obsolete;
			}

			enum "aerserv" {
				opd:help "AerServ is a free mobile SSP and monetization platform";
				status obsolete;
			}

			enum "afl" {
				opd:help "Australian Footy League website";
				status obsolete;
			}

			enum "afp" {
				opd:help "Apple Filing Protocol (AFP) is a file sharing protocol used on Mac";
				status obsolete;
			}

			enum "afreeca" {
				opd:help "Afreeca TV (Any FREE broadCAsting TV) is a P2P-based video streaming service based in South Korea";
				status obsolete;
			}

			enum "africaguinee" {
				opd:help "Information web portal on Guinea and Africa";
				status obsolete;
			}

			enum "afrikmag" {
				opd:help "African news website featuring articles about politics, cultural events, economy, sports, etc";
				status obsolete;
			}

			enum "aftenposten" {
				opd:help "Norwegian news portal";
				status obsolete;
			}

			enum "aftonbladet" {
				opd:help "Swedish news portal";
				status obsolete;
			}

			enum "agame" {
				opd:help "Gaming portal operated by the Dutch company Spilgames";
				status obsolete;
			}

			enum "ah" {
				opd:help "(Deprecated) The AH protocol (Authentication Header) is found over the IP layer (IANA protocol number: 51)";
				status obsolete;
			}

			enum "aiaigame" {
				opd:help "Aurora Interactive, a Chinese vendor of 3D games";
				status obsolete;
			}

			enum "aib" {
				opd:help "Irish banking website";
				status obsolete;
			}

			enum "aiccu_tic" {
				opd:help "AICCU (Automatic IPv6 Connectivity Client Utility) is a cross-platform utility for automatic IPv6 tunnels configuration";
				status obsolete;
			}

			enum "aili" {
				opd:help "Chinese fashion shopping website";
				status obsolete;
			}

			enum "aim" {
				opd:help "AIM (originally AOL Instant Messenger) is an instant messaging application";
				status obsolete;
			}

			enum "aim_express" {
				opd:help "(Deprecated) AOL Instant Messaging Express supports many of the standard features included in AIM, but does not provide advanced features like file transfer, audio chat or video conferencing";
				status obsolete;
			}

			enum "aim_transfer" {
				opd:help "AIM is an instant messaging protocol";
				status obsolete;
			}

			enum "aimini" {
				opd:help "Aimini is an online solution to store, send and share files";
				status obsolete;
			}

			enum "aims" {
				opd:help "AIMS is the secure version of AIM";
				status obsolete;
			}

			enum "air_video" {
				opd:help "Air Video is a streaming video player for iOS";
				status obsolete;
			}

			enum "airaim" {
				opd:help "This classifies the HTTP traffic to the host airaim.com";
				status obsolete;
			}

			enum "airkast" {
				opd:help "AirKast is a large mobile publisher and ad network for broadcasters and media companies in the US";
				status obsolete;
			}

			enum "aizhan" {
				opd:help "Chinese website";
				status obsolete;
			}

			enum "akamai" {
				opd:help "Akamai is a major content delivery network (CDN) and distributed services provider, including cloud, etc";
				status obsolete;
			}

			enum "akinator" {
				opd:help "Akinator is an online game and mobile app based on Twenty Questions";
				status obsolete;
			}

			enum "akipress" {
				opd:help "Kyrgyzstani news portal";
				status obsolete;
			}

			enum "akoam" {
				opd:help "Famous pirate movie streaming website in Yemen";
				status obsolete;
			}

			enum "aktuality" {
				opd:help "Slovak news portal";
				status obsolete;
			}

			enum "alakhbar" {
				opd:help "Mauritanian news portal";
				status obsolete;
			}

			enum "alaraby" {
				opd:help "Qatari news portal";
				status obsolete;
			}

			enum "alayam24" {
				opd:help "News website in Morocco";
				status obsolete;
			}

			enum "albawabhnews" {
				opd:help "Egyptian news portal";
				status obsolete;
			}

			enum "alexa" {
				opd:help "Alexa provides web analytics and statistics";
				status obsolete;
			}

			enum "alfajertv" {
				opd:help "Palestinian news portal";
				status obsolete;
			}

			enum "alibaba" {
				opd:help "Alibaba is a large online business-to-business trading platform for small businesses";
				status obsolete;
			}

			enum "aliexpress" {
				opd:help "Chinese ecommerce website";
				status obsolete;
			}

			enum "alimama" {
				opd:help "Alimama is an advertiser in China, the company belongs to the Alibaba Group";
				status obsolete;
			}

			enum "alipay" {
				opd:help "AliPay is an online-payment platform owned by the Alibaba Group";
				status obsolete;
			}

			enum "aljaras" {
				opd:help "Lebanese entertainment website/magazine";
				status obsolete;
			}

			enum "aljarida" {
				opd:help "Kuwaiti news portal";
				status obsolete;
			}

			enum "aljazeera" {
				opd:help "Aljazeera Media Group website (not to be confused with aljazeera.com, the English speaking news channel)";
				status obsolete;
			}

			enum "alkawnnews" {
				opd:help "Jordanian news portal";
				status obsolete;
			}

			enum "all_slots_casino" {
				opd:help "Online casino";
				status obsolete;
			}

			enum "allegro" {
				opd:help "Polish shopping web portal";
				status obsolete;
			}

			enum "allmusic" {
				opd:help "Allmusic is an online music guide";
				status obsolete;
			}

			enum "allocine" {
				opd:help "French website Allocine, a reference for movie showtimes, reviews, and movie/series news";
				status obsolete;
			}

			enum "almanar" {
				opd:help "Lebanese news portal";
				status obsolete;
			}

			enum "almashhad" {
				opd:help "Yemenite news portal";
				status obsolete;
			}

			enum "almasryalyoum" {
				opd:help "Egyptian news portal";
				status obsolete;
			}

			enum "alnilin" {
				opd:help "Sudanese news portal";
				status obsolete;
			}

			enum "alquds" {
				opd:help "Palestinian news portal";
				status obsolete;
			}

			enum "alrakoba" {
				opd:help "Sudanese news portal";
				status obsolete;
			}

			enum "alsjl" {
				opd:help "Yemenite news portal";
				status obsolete;
			}

			enum "altiris" {
				opd:help "Altiris provides service-oriented management solutions which allow managing IT infrastructures";
				status obsolete;
			}

			enum "alwafd" {
				opd:help "Egyptian news portal";
				status obsolete;
			}

			enum "alwakeelnews" {
				opd:help "Jordanian news portal";
				status obsolete;
			}

			enum "alwasatnews" {
				opd:help "Bahraini news portal";
				status obsolete;
			}

			enum "alwatanvoice" {
				opd:help "Palestinian news portal";
				status obsolete;
			}

			enum "alyamanalaraby" {
				opd:help "Worldwide news website famous in the Yemen";
				status obsolete;
			}

			enum "alyaoum24" {
				opd:help "Moroccan news portal";
				status obsolete;
			}

			enum "amazon" {
				opd:help "This classifies the generic web traffic related to Amazon services";
				status obsolete;
			}

			enum "amazon_adsystem" {
				opd:help "This classifies the traffic related to Amazon advertising services";
				status obsolete;
			}

			enum "amazon_aws" {
				opd:help "Amazon AWS is a cloud-computing platform offered by Amazon, that includes Amazon Elastic Compute Cloud (EC2) and Amazon Simple Storage Service (S3)";
				status obsolete;
			}

			enum "amazon_chime" {
				opd:help "Amazon Chime is a fully-managed communications service in the cloud";
				status obsolete;
			}

			enum "amazon_cloud_drive" {
				opd:help "Amazon Cloud Drive is a cloud application which allows photos and videos storage";
				status obsolete;
			}

			enum "amazon_mp3" {
				opd:help "(Deprecated) Amazon MP3 is an online music store owned and operated by Amazon.com";
				status obsolete;
			}

			enum "amazon_music" {
				opd:help "Amazon Music is an online music store";
				status obsolete;
			}

			enum "amazon_video" {
				opd:help "Amazon Prime Video is an online video on demand service owned and operated by Amazon";
				status obsolete;
			}

			enum "ambebi" {
				opd:help "Georgian news portal";
				status obsolete;
			}

			enum "ameba" {
				opd:help "Ameba is a Japanese web and mobile portal providing a blogging platform, a virtual community, and social gaming";
				status obsolete;
			}

			enum "americanexpress" {
				opd:help "Websites of American Express, a company that issues credit cards and provides various financial and commercial services";
				status obsolete;
			}

			enum "ami" {
				opd:help "Institutional news web portal in Mauritania";
				status obsolete;
			}

			enum "amie_street" {
				opd:help "(Deprecated) This is deprecated";
				status obsolete;
			}

			enum "amjilt" {
				opd:help "Mongolian news portal";
				status obsolete;
			}

			enum "ammonnews" {
				opd:help "Jordanian news portal";
				status obsolete;
			}

			enum "ammyy_admin" {
				opd:help "Ammyy Admin is a remote desktop application";
				status obsolete;
			}

			enum "amoebaos" {
				opd:help "AmoebaOS is an online operating system, providing a cloud-based desktop";
				status obsolete;
			}

			enum "amplitude" {
				opd:help "Amplitude is a web and mobile analytics platform";
				status obsolete;
			}

			enum "amqp" {
				opd:help "AMQP (Advanced Message Queuing Protocol) is an open standard application layer protocol for message-oriented middleware";
				status obsolete;
			}

			enum "andornet" {
				opd:help "Web services provider in Andorra";
				status obsolete;
			}

			enum "android_cnxmgr" {
				opd:help "Android connectivity manager is used by an android device to periodically check and manage internet connection";
				status obsolete;
			}

			enum "angry_birds" {
				opd:help "Angry Birds is a mobile game edited by Rovio";
				status obsolete;
			}

			enum "animebw" {
				opd:help "BitTorrent tracker search engine";
				status obsolete;
			}

			enum "animoto" {
				opd:help "Animoto automatically produces video pieces from photos, video clips, and music";
				status obsolete;
			}

			enum "anipang" {
				opd:help "Anipang for Kakao is a South Korean mobile puzzle game based on the Kakao Talk social networking system";
				status obsolete;
			}

			enum "annapurnapost" {
				opd:help "News portal with up-to-date news from Nepal on politics, social affairs, etc";
				status obsolete;
			}

			enum "annonces" {
				opd:help "Classified ads web portal from New Caledonia";
				status obsolete;
			}

			enum "anobii" {
				opd:help "Anobii is an online personal book library indexing and management service";
				status obsolete;
			}

			enum "anspress" {
				opd:help "Azerbaijani news portal";
				status obsolete;
			}

			enum "answers" {
				opd:help "American knowledge-sharing website for internet users";
				status obsolete;
			}

			enum "ant1iwo" {
				opd:help "Cypriot news portal";
				status obsolete;
			}

			enum "ants_p2p" {
				opd:help "Ants is a distributed third-generation peer-to-peer client, allowing anonymization by hiding IP addresses and encrypting transmitted data";
				status obsolete;
			}

			enum "any_0hop" {
				opd:help "The any_0hop protocol (Any 0-hop protocol) is found over the IP layer (IANA protocol number: 114)";
				status obsolete;
			}

			enum "anydesk" {
				opd:help "AnyDesk is a remote desktop control solution which allows bidirectional remote access between Windows, Mac OS, Linux and FreeBSD computers";
				status obsolete;
			}

			enum "anz" {
				opd:help "Offers home, car, and business loans, as well as internet banking, and insurance";
				status obsolete;
			}

			enum "anzhi" {
				opd:help "Chinese mobile device games and forums";
				status obsolete;
			}

			enum "aol" {
				opd:help "This classifies the traffic related to the AOL portal or to the AOL advertising services";
				status obsolete;
			}

			enum "aol_on" {
				opd:help "AOL On is a video streaming website";
				status obsolete;
			}

			enum "aol_one" {
				opd:help "AOL One is a programmatic video advertising solutions company owned by AOL";
				status obsolete;
			}

			enum "apa" {
				opd:help "Azerbaijani news portal";
				status obsolete;
			}

			enum "aparat" {
				opd:help "Iranian multimedia website";
				status obsolete;
			}

			enum "apns" {
				opd:help "Apple Push Notification Service is an Apple service which forwards notifications from the servers of third party applications to iOS devices";
				status obsolete;
			}

			enum "apollo" {
				opd:help "Apollo is the routing protocol implemented natively in Apollo workstations";
				status obsolete;
			}

			enum "apollo_lv" {
				opd:help "Latvian news portal";
				status obsolete;
			}

			enum "appbot" {
				opd:help "Appbot aggregates app store reviews for all countries on the iTunes, Google Play and Amazon app stores";
				status obsolete;
			}

			enum "appchina" {
				opd:help "Chinese Android application market";
				status obsolete;
			}

			enum "apple" {
				opd:help "This classifies the generic traffic related to Apple's web portal and content delivery services";
				status obsolete;
			}

			enum "apple_airplay" {
				opd:help "Apple airplay is a protocol for display picture and video to a connected TV from a device connected to the same private network";
				status obsolete;
			}

			enum "apple_airport" {
				opd:help "Apple Airport is a protocol aiming to configure a wireless device";
				status obsolete;
			}

			enum "apple_airprint" {
				opd:help "Apple Airprint is a network printing feature for Apple systems";
				status obsolete;
			}

			enum "apple_hls" {
				opd:help "Apple implementation of the HTTP Live Streaming IETF draft";
				status obsolete;
			}

			enum "apple_location" {
				opd:help "Apple Location is used to provide information about the location of an Apple device";
				status obsolete;
			}

			enum "apple_maps" {
				opd:help "Apple Maps is a proprietary map application for iOS 6 devices";
				status obsolete;
			}

			enum "apple_music" {
				opd:help "Apple Music is an on-demand music streaming service by Apple";
				status obsolete;
			}

			enum "apple_siri" {
				opd:help "Advanced voice recognition system used on some Apple iPhone devices";
				status obsolete;
			}

			enum "apple_update" {
				opd:help "Apple_update is the protocol used for Apple software updates";
				status obsolete;
			}

			enum "appledaily" {
				opd:help "Taiwanese news portal";
				status obsolete;
			}

			enum "applejuice" {
				opd:help "AppleJuice is a peer-to-peer file exchange protocol similar to E-Donkey";
				status obsolete;
			}

			enum "applovin" {
				opd:help "Applovin is a mobile marketing company";
				status obsolete;
			}

			enum "appnexus" {
				opd:help "AppNexus is an internet advertising technology and solution";
				status obsolete;
			}

			enum "appsflyer" {
				opd:help "AppsFlyer provides measurement and tracking services for mobile platform application developers";
				status obsolete;
			}

			enum "appshopper" {
				opd:help "Mac Apps, Mac App Store, iPad, iPhone and iPod touch app store listings, news, and price drops";
				status obsolete;
			}

			enum "appstore" {
				opd:help "The Apple App Store is a digital application distribution platform for iOS developed and maintained by Apple Inc";
				status obsolete;
			}

			enum "aprod" {
				opd:help "(Deprecated) Hungarian free classifieds website";
				status obsolete;
			}

			enum "apsalar" {
				opd:help "Apsalar provides analytics and advertising solutions for mobile application developers";
				status obsolete;
			}

			enum "aptoide" {
				opd:help "Aptoide is a large alternative marketplace for Android mobile apps, allowing users to setup and manage their own Android stores";
				status obsolete;
			}

			enum "aqlame" {
				opd:help "Mauritanian news portal";
				status obsolete;
			}

			enum "arabiaweather" {
				opd:help "Jordanian meteorological portal";
				status obsolete;
			}

			enum "archive" {
				opd:help "Archive.org is building a digital library of Internet sites and other cultural artefacts in digital form";
				status obsolete;
			}

			enum "arenabg" {
				opd:help "Bulgarian pirate movie torrent search engine, also featuring a video player (P2P)";
				status obsolete;
			}

			enum "ares" {
				opd:help "Ares is a peer-to-peer protocol";
				status obsolete;
			}

			enum "areyouahuman" {
				opd:help "Real time human input detection service for websites and applications";
				status obsolete;
			}

			enum "argaam" {
				opd:help "Saudi stock exchange information website";
				status obsolete;
			}

			enum "argus" {
				opd:help "The argus protocol (ARGUS) is found over the IP layer (IANA protocol number: 13)";
				status obsolete;
			}

			enum "aris" {
				opd:help "The aris protocol (ARIS) is found over the IP layer (IANA protocol number: 104)";
				status obsolete;
			}

			enum "armorgames" {
				opd:help "ArmorGames.com is a free on-line flash-based video game site";
				status obsolete;
			}

			enum "armorgames_play" {
				opd:help "Classifies requests to play games on ArmorGames.com";
				status obsolete;
			}

			enum "asana" {
				opd:help "Asana is a web and mobile application designed to improve the way teams communicate and collaborate";
				status obsolete;
			}

			enum "asiae" {
				opd:help "Korean investment and market news website";
				status obsolete;
			}

			enum "asiandvdclub" {
				opd:help "BitTorrent tracker search engine";
				status obsolete;
			}

			enum "ask" {
				opd:help "American website with a search engine which lists answers to internet users questions";
				status obsolete;
			}

			enum "ask_fm" {
				opd:help "International Social network";
				status obsolete;
			}

			enum "askcom" {
				opd:help "Global news website popular in Algeria";
				status obsolete;
			}

			enum "asmallworld" {
				opd:help "ASmallworld is an American private social club about travel";
				status obsolete;
			}

			enum "asproxy" {
				opd:help "ASProxy is a free and open-source web proxy which allows the user to surf the net anonymously";
				status obsolete;
			}

			enum "atalk" {
				opd:help "The AppleTalk Protocol Suite implements services for routing, file transfer, printer sharing and emails in Apple environments";
				status obsolete;
			}

			enum "athlinks" {
				opd:help "Athlinks is an American social network for athletes, swimmers and more";
				status obsolete;
			}

			enum "atlasinfo" {
				opd:help "Mauritanian news portal";
				status obsolete;
			}

			enum "atlassian" {
				opd:help "Atlassian is an Australian enterprise software company that develops products geared towards software developers and project managers, known for its issue-tracking application named Jira";
				status obsolete;
			}

			enum "atlassolutions" {
				opd:help "Atlas Solutions is a subsidiary of Facebook which provides services in online advertising";
				status obsolete;
			}

			enum "att" {
				opd:help "AT&T is an American telecommunications company";
				status obsolete;
			}

			enum "atwiki" {
				opd:help "Japanese website design service and wiki hosting";
				status obsolete;
			}

			enum "auction" {
				opd:help "Auction website service operated by Auction Co, a South Korean company (bought by the eBay group in 2001)";
				status obsolete;
			}

			enum "audible" {
				opd:help "Audible Inc. is a seller and producer of spoken audio entertainment owned by Amazon";
				status obsolete;
			}

			enum "aufeminin" {
				opd:help "Aufeminin is a website and French media group targeting women in particular";
				status obsolete;
			}

			enum "auone" {
				opd:help "Multi services web portal owned by KDDI";
				status obsolete;
			}

			enum "auto24" {
				opd:help "Estonian classified ads website specialised in motor vehicles and spare parts";
				status obsolete;
			}

			enum "autodesk" {
				opd:help "Fusion 360 is a SaaS CAM and CAD application edited by Autodesk";
				status obsolete;
			}

			enum "avas" {
				opd:help "Web news portal from Maldives";
				status obsolete;
			}

			enum "avast" {
				opd:help "Family of internet security applications developed by Avast Software";
				status obsolete;
			}

			enum "avatars_united" {
				opd:help "(Deprecated) This is deprecated";
				status obsolete;
			}

			enum "avaz" {
				opd:help "Croatian news portal";
				status obsolete;
			}

			enum "avg" {
				opd:help "Antivirus and security software products for home and business users";
				status obsolete;
			}

			enum "avg_update" {
				opd:help "Protocol used for AVG software updates";
				status obsolete;
			}

			enum "avira_update" {
				opd:help "Avira_update is the protocol used for Avira software updates";
				status obsolete;
			}

			enum "avito_ma" {
				opd:help "Free Moroccan classified ads";
				status obsolete;
			}

			enum "avito_ru" {
				opd:help "Free Russian classified ads";
				status obsolete;
			}

			enum "avoidr" {
				opd:help "Avoidr is a free web proxy";
				status obsolete;
			}

			enum "avto" {
				opd:help "Slovenian vehicle related classifieds";
				status obsolete;
			}

			enum "awempire" {
				opd:help "Awempire is an adult affiliate program for webmasters";
				status obsolete;
			}

			enum "ax25" {
				opd:help "The ax25 protocol (AX.25 Frames) is found over the IP layer (IANA protocol number: 93)";
				status obsolete;
			}

			enum "axifile" {
				opd:help "(Deprecated) AXifile is a file sharing service";
				status obsolete;
			}

			enum "azet" {
				opd:help "Slovak web portal";
				status obsolete;
			}

			enum "azetone" {
				opd:help "Azetone is a complete platform that allows to fully analyze, optimize and personalize mobile applications";
				status obsolete;
			}

			enum "b92" {
				opd:help "Serbian news portal";
				status obsolete;
			}

			enum "babelgum" {
				opd:help "(Deprecated) This classifies the HTTP traffic to the host babelgum.com";
				status obsolete;
			}

			enum "babycenter" {
				opd:help "BabyCenter is a parenting web platform providing help about pregnancy, birth, etc";
				status obsolete;
			}

			enum "babyhome" {
				opd:help "Taiwanese pregnancy and parenting information, albums and parenting diaries";
				status obsolete;
			}

			enum "babylon" {
				opd:help "Babylon is a global provider of language and search solutions";
				status obsolete;
			}

			enum "backpackers" {
				opd:help "Popular Taiwanese tourist site, backpacking forum, cheap flights parity Reservation parity";
				status obsolete;
			}

			enum "badongo" {
				opd:help "Badongo is an online solution to store, send and share files";
				status obsolete;
			}

			enum "badoo" {
				opd:help "Badoo is a dating oriented social networking website";
				status obsolete;
			}

			enum "baganmart" {
				opd:help "Myanmar B2B ecommerce platform for trading and business networking";
				status obsolete;
			}

			enum "baidu" {
				opd:help "Baidu is a Chinese search engine for websites, audio files and images";
				status obsolete;
			}

			enum "baidu_hi_games" {
				opd:help "Chinese online game site, Flash and HTML5 based";
				status obsolete;
			}

			enum "baidu_maps" {
				opd:help "Baidu Maps is a web mapping service application and technology provided by Baidu akin to Google Maps";
				status obsolete;
			}

			enum "baidu_player" {
				opd:help "BaiduPlayer is a video player that can play local, online and OnDemand videos";
				status obsolete;
			}

			enum "baidu_wallet" {
				opd:help "Baidu Wallet is an application of money management";
				status obsolete;
			}

			enum "baike" {
				opd:help "Interactive encyclopedia online encyclopedia based on the Chinese Wikipedia";
				status obsolete;
			}

			enum "balkanweb" {
				opd:help "Albanian news portal";
				status obsolete;
			}

			enum "banco_industrial" {
				opd:help "Banking website in Guatemala";
				status obsolete;
			}

			enum "bancoestado" {
				opd:help "Website of a bank in Chile";
				status obsolete;
			}

			enum "bancopopular" {
				opd:help "Puertorican online banking website";
				status obsolete;
			}

			enum "banesc_online" {
				opd:help "Venezualian online banking website";
				status obsolete;
			}

			enum "banglanews24" {
				opd:help "Bangladeshi news portal";
				status obsolete;
			}

			enum "bankmellat" {
				opd:help "Iranian Banking website";
				status obsolete;
			}

			enum "banvenez" {
				opd:help "Web portal of a bank in Venezuela";
				status obsolete;
			}

			enum "baofeng" {
				opd:help "Chinese video streaming portal";
				status obsolete;
			}

			enum "base" {
				opd:help "Base is a virtual protocol that is always present at the beginning of the protocol path";
				status obsolete;
			}

			enum "battlenet" {
				opd:help "Online multiplayer gaming server";
				status obsolete;
			}

			enum "bazaarvoice" {
				opd:help "Bazaarvoice provides to companies solutions to gather consumer reviews and boost their sales";
				status obsolete;
			}

			enum "bazos" {
				opd:help "Classified ads website in Czech republic";
				status obsolete;
			}

			enum "bbc" {
				opd:help "The BBC Homepage providing News and Broadcast";
				status obsolete;
			}

			enum "bbc_player" {
				opd:help "BBC Player is an in-browser live video streaming service";
				status obsolete;
			}

			enum "bbm" {
				opd:help "BBM is the messenger/VoIP/Video protocol for blackberry";
				status obsolete;
			}

			enum "bbm_audio" {
				opd:help "bbm_audio is the VoIP layer of the BlackBerry's messenger";
				status obsolete;
			}

			enum "bbm_video" {
				opd:help "BBM_video is the video layer of the BlackBerry's messenger";
				status obsolete;
			}

			enum "bbn_rcc_mon" {
				opd:help "The bbn_rcc_mon protocol (BBN RCC Monitoring) is found over the IP layer (IANA protocol number: 10)";
				status obsolete;
			}

			enum "bbs" {
				opd:help "News portal of a National TV and radio broadcast agency from Bhutan";
				status obsolete;
			}

			enum "bca_co" {
				opd:help "Indonesian-operated website that offers banking services of Bank Central Asia";
				status obsolete;
			}

			enum "bd24live" {
				opd:help "Online news portal in Bangladesh";
				status obsolete;
			}

			enum "bdjobs" {
				opd:help "Large job site in Bangladesh for job seeking and career counseling";
				status obsolete;
			}

			enum "bdnews24" {
				opd:help "Bangladeshi news portal";
				status obsolete;
			}

			enum "beanfun" {
				opd:help "Large Taiwanese game portal, a single account to log into all games";
				status obsolete;
			}

			enum "beatport" {
				opd:help "On-line music shop website";
				status obsolete;
			}

			enum "bebo" {
				opd:help "Bebo is a social networking website, enabling users to connect to relatives, friends, or unknown people";
				status obsolete;
			}

			enum "bebo_mail" {
				opd:help "Bebo is a social networking website";
				status obsolete;
			}

			enum "beetalk" {
				opd:help "beetalk is an instant messaging software for mobile";
				status obsolete;
			}

			enum "beforward" {
				opd:help "Classified ads of Japanese used cars";
				status obsolete;
			}

			enum "beirutpress" {
				opd:help "News web portal located in Lebanon";
				status obsolete;
			}

			enum "bemaniso" {
				opd:help "BitTorrent tracker search engine";
				status obsolete;
			}

			enum "bernews" {
				opd:help "Bermudan news portal";
				status obsolete;
			}

			enum "berniaga" {
				opd:help "(Deprecated) This classifies the HTTP traffic to the host berniaga.com";
				status obsolete;
			}

			enum "bestsharing_com" {
				opd:help "(Deprecated) Classifies web browsing on the bestsharing.com Direct DownLoad links service";
				status obsolete;
			}

			enum "bet365" {
				opd:help "Online betting site";
				status obsolete;
			}

			enum "bet9ja" {
				opd:help "Famous sport betting website in Nigeria";
				status obsolete;
			}

			enum "bgp" {
				opd:help "Border Gateway Protocol (BGP) is an inter Autonomous Systems routing protocol used by most ISPs";
				status obsolete;
			}

			enum "bidorbuy" {
				opd:help "South African auction and shopping website";
				status obsolete;
			}

			enum "bidswitch" {
				opd:help "Bidswitch provides immediate and seamless real-time access for Supply and Demand Partners across all media types";
				status obsolete;
			}

			enum "big5_sporting_goods" {
				opd:help "Online sport goods store";
				status obsolete;
			}

			enum "bigadda" {
				opd:help "(Deprecated) This classifies the HTTP traffic to the host bigadda.com";
				status obsolete;
			}

			enum "bigeye" {
				opd:help "Ugandan entertainment website";
				status obsolete;
			}

			enum "biglobe_ne" {
				opd:help "Japanese web portal and search site";
				status obsolete;
			}

			enum "bigpond_movies" {
				opd:help "Australian video streaming platform owned by Telstra Media, that streams live and on-demand services like BigPond Movies, AFL, or NRL";
				status obsolete;
			}

			enum "bigtent" {
				opd:help "Social network for parents operated by Care.com, an American company";
				status obsolete;
			}

			enum "bigupload" {
				opd:help "Adult video hosting website";
				status obsolete;
			}

			enum "biip" {
				opd:help "Norwegian community-based website which is owned by TV2, a Television company";
				status obsolete;
			}

			enum "bikhir" {
				opd:help "Moroccan classified ads";
				status obsolete;
			}

			enum "bild" {
				opd:help "German news portal";
				status obsolete;
			}

			enum "bing" {
				opd:help "This protocol is used for sending user queries to the Bing search engine";
				status obsolete;
			}

			enum "bint_jbeil" {
				opd:help "Lebanon news website";
				status obsolete;
			}

			enum "biobiochile" {
				opd:help "Chilean news portal";
				status obsolete;
			}

			enum "bitbucket" {
				opd:help "Bitbucket is a free code DVCS hosting site for Git and Mercurial";
				status obsolete;
			}

			enum "bitcoin" {
				opd:help "Bitcoin is a distributed payment system";
				status obsolete;
			}

			enum "bitcomet_pex" {
				opd:help "In a bitcomet file sharing networks, this Peer Exchange (PEX) protocol is used to help maintain a swarm of peers that are collaborating to share a given torrent";
				status obsolete;
			}

			enum "bitdefender_update" {
				opd:help "BitDefender_update is the protocol used for BitDefender software updates";
				status obsolete;
			}

			enum "bitenova" {
				opd:help "BitTorrent tracker search engine";
				status obsolete;
			}

			enum "bithq" {
				opd:help "(Deprecated) BitTorrent tracker search engine";
				status obsolete;
			}

			enum "bitlord" {
				opd:help "BitLord is a free BitTorrent client";
				status obsolete;
			}

			enum "bitme" {
				opd:help "BitTorrent tracker search engine";
				status obsolete;
			}

			enum "bitmedianetwork" {
				opd:help "Bitmedianetwork is the advertising service provided by BitTorrent";
				status obsolete;
			}

			enum "bitmetv" {
				opd:help "BitTorrent tracker search engine";
				status obsolete;
			}

			enum "bits" {
				opd:help "Background Intelligent Transfer Service (BITS) transfers files (downloads or uploads) between a client and server and provides progress information related to the transfers";
				status obsolete;
			}

			enum "bitseduce" {
				opd:help "BitTorrent tracker search engine";
				status obsolete;
			}

			enum "bitshock" {
				opd:help "BitTorrent tracker search engine";
				status obsolete;
			}

			enum "bitsoup" {
				opd:help "BitTorrent tracker search engine";
				status obsolete;
			}

			enum "bitstrips" {
				opd:help "BitStrips allows to design cartoon versions of yourself and your friends";
				status obsolete;
			}

			enum "bittorrent" {
				opd:help "BitTorrent is a peer-to-peer protocol";
				status obsolete;
			}

			enum "bittorrent_application" {
				opd:help "BitTorrent Apps web resources access from the BitTorrent application";
				status obsolete;
			}

			enum "bittorrent_bundle" {
				opd:help "BitTorrent Bundle is a BitTorrent-sponsored torrent file download platform";
				status obsolete;
			}

			enum "bitvaulttorrent" {
				opd:help "BitTorrent tracker search engine";
				status obsolete;
			}

			enum "bitworld" {
				opd:help "BitTorrent tracker search engine";
				status obsolete;
			}

			enum "bizographics" {
				opd:help "bizographics.com is a domain used by Bizo which is an advertising company that is part of a network of sites, cookies, and other technologies used to track you, what you do and what you click on, as you go from site to site, surfing the Web";
				status obsolete;
			}

			enum "bjnp" {
				opd:help "BJNP refers to a printer protocol used by printers made by Canon";
				status obsolete;
			}

			enum "blackberry" {
				opd:help "This protocol refers to all Blackberry mobile device communications over wifi";
				status obsolete;
			}

			enum "blackberry_locate" {
				opd:help "This protocol refers to all Blackberry mobile device communications about localization over wifi";
				status obsolete;
			}

			enum "blackberry_update" {
				opd:help "This protocol classifies the Blackberry 10 family OS software updates";
				status obsolete;
			}

			enum "blackplanet" {
				opd:help "Blackplanet is a social network service for African-Americans in particular";
				status obsolete;
			}

			enum "blastingnews" {
				opd:help "Blasting News is a global social news web magazine";
				status obsolete;
			}

			enum "bleacherreport" {
				opd:help "Bleacher Report is a sports news website";
				status obsolete;
			}

			enum "bleep" {
				opd:help "Bleep is a fully encrypted and distributed instant messaging protocol created by the BitTorrent team";
				status obsolete;
			}

			enum "blic" {
				opd:help "Serbian news portal";
				status obsolete;
			}

			enum "blick" {
				opd:help "Swiss news portal";
				status obsolete;
			}

			enum "blip_tv" {
				opd:help "(Deprecated) This classified the traffic to the Blip video streaming service (shut down in August 2015)";
				status obsolete;
			}

			enum "blockbuster" {
				opd:help "(Deprecated) This classifies the HTTP traffic to the host blockbuster.com";
				status obsolete;
			}

			enum "blocket" {
				opd:help "Swedish local classified ads";
				status obsolete;
			}

			enum "blog" {
				opd:help "Hungarian blog hosting website";
				status obsolete;
			}

			enum "blogdetik" {
				opd:help "(Deprecated) This classifies the HTTP traffic to the host blogdetik.com";
				status obsolete;
			}

			enum "blogfa" {
				opd:help "Persian Blog Hosting";
				status obsolete;
			}

			enum "blogger" {
				opd:help "Blogger (formerly Blogspot) is a blog-publishing service that allows multi-user blogs with time-stamped entries";
				status obsolete;
			}

			enum "blogimg" {
				opd:help "Japanese blog site";
				status obsolete;
			}

			enum "blogphongthuy" {
				opd:help "Specialized classified ads website in Vietnam";
				status obsolete;
			}

			enum "blogspot" {
				opd:help "(Deprecated) This classifies the HTTP traffic to the host blogspot.com";
				status obsolete;
			}

			enum "blogster" {
				opd:help "Website that offers blogging services and resources for bloggers";
				status obsolete;
			}

			enum "blokus" {
				opd:help "Website for a popular family board game of Mattel, Inc";
				status obsolete;
			}

			enum "bloomberg" {
				opd:help "Bloomberg is a website about business and financial news";
				status obsolete;
			}

			enum "blubster" {
				opd:help "Blubster is a peer-to-peer music file sharing software";
				status obsolete;
			}

			enum "bluejayfilms" {
				opd:help "Web page operated by a Portland Oregon based company focused on producing films";
				status obsolete;
			}

			enum "bluewin" {
				opd:help "Swiss news portal";
				status obsolete;
			}

			enum "bmff" {
				opd:help "The ISO Base Media File Format, as described in ISO/IEC 14496-12:2008 (MPEG-4 Part 12)";
				status obsolete;
			}

			enum "bna" {
				opd:help "The bna protocol (BNA) is found over the IP layer (IANA protocol number: 49)";
				status obsolete;
			}

			enum "bofa" {
				opd:help "Signature which classifies user access to the Bank of America online service";
				status obsolete;
			}

			enum "boldchat" {
				opd:help "BoldChat is an instant messaging platform for businesses (by LogMeIn)";
				status obsolete;
			}

			enum "bolha" {
				opd:help "Slovenian local classified ads";
				status obsolete;
			}

			enum "bolt" {
				opd:help "Electronic payments website";
				status obsolete;
			}

			enum "bomb01" {
				opd:help "Website about Hong Kongese youth interest and lifestyle related content";
				status obsolete;
			}

			enum "bondisk" {
				opd:help "Site for downloading videos";
				status obsolete;
			}

			enum "bongacams" {
				opd:help "Adult video content website";
				status obsolete;
			}

			enum "bonmarche" {
				opd:help "Online shopping site in Madagascar";
				status obsolete;
			}

			enum "bonpoo" {
				opd:help "(Deprecated) Online photo-sharing service";
				status obsolete;
			}

			enum "booking" {
				opd:help "Lodging reservations website";
				status obsolete;
			}

			enum "books" {
				opd:help "Taiwanese on-line books store";
				status obsolete;
			}

			enum "books_iread" {
				opd:help "(Deprecated) This classified the HTTP traffic to the host weread.com";
				status obsolete;
			}

			enum "bootstrapcdn" {
				opd:help "BootstrapCDN is a free and public content delivery network";
				status obsolete;
			}

			enum "bootytape" {
				opd:help "BitTorrent tracker search engine";
				status obsolete;
			}

			enum "box_net" {
				opd:help "Box is a secured file hosting and sharing web service, available from desktop and mobile platforms";
				status obsolete;
			}

			enum "boxopus" {
				opd:help "Boxopus securely downloads torrents into the private space or in the cloud";
				status obsolete;
			}

			enum "br_sat_mon" {
				opd:help "The br_sat_mon protocol (Backroom SATNET Monitoring) is found over the IP layer (IANA protocol number: 76)";
				status obsolete;
			}

			enum "braintree" {
				opd:help "Braintree is a PayPal company which provides payment processing options for many devices";
				status obsolete;
			}

			enum "branch" {
				opd:help "Branch Metrics is a deep linking and business analytics platform offering developer tools for large and independent mobile application companies";
				status obsolete;
			}

			enum "brazzers" {
				opd:help "Brazzers is an adult website";
				status obsolete;
			}

			enum "brightcove" {
				opd:help "Brightcove is a provider of cloud services for video";
				status obsolete;
			}

			enum "brightroll" {
				opd:help "BrightRoll is a video advertising software system developed by a company that became a subsidiary of Yahoo";
				status obsolete;
			}

			enum "brighttalk" {
				opd:help "Video site of webinars from business experts";
				status obsolete;
			}

			enum "browntracker" {
				opd:help "BitTorrent tracker search engine";
				status obsolete;
			}

			enum "bsp" {
				opd:help "Popular banking web portal in South Pacific";
				status obsolete;
			}

			enum "bssap" {
				opd:help "BSSAP is a telephony protocol used in SS7 networks";
				status obsolete;
			}

			enum "bt_bt" {
				opd:help "Bhutan Telecom Limited (BTL) is a provider of telecommunications and Internet services in the Kingdom of Bhutan";
				status obsolete;
			}

			enum "bt_chat" {
				opd:help "(Deprecated) BitTorrent tracker search engine";
				status obsolete;
			}

			enum "bt_dk" {
				opd:help "Danish news portal";
				status obsolete;
			}

			enum "bt_wrzru" {
				opd:help "BitTorrent tracker search engine";
				status obsolete;
			}

			enum "btjunkie" {
				opd:help "BitTorrent tracker search engine";
				status obsolete;
			}

			enum "buddybuddy" {
				opd:help "(Deprecated) This classified the HTTP traffic to the host buddybuddy.co.kr";
				status obsolete;
			}

			enum "bugs" {
				opd:help "Korean music platform operated by Bucks Ltd";
				status obsolete;
			}

			enum "bugsnag" {
				opd:help "Bugsnag detects crashes and other errors in real-time from web and mobile applications";
				status obsolete;
			}

			enum "bujumbura" {
				opd:help "News agency blog in Burundi";
				status obsolete;
			}

			enum "bukalapak" {
				opd:help "Indonesian classified ads website";
				status obsolete;
			}

			enum "bulawayo24" {
				opd:help "Breaking News from Bulawayo, Zimbabwe and worldwide updates";
				status obsolete;
			}

			enum "burt" {
				opd:help "Burt is a web analytics platform";
				status obsolete;
			}

			enum "businessweek" {
				opd:help "(Deprecated) Classifies HTTP traffic to the host businessweek.com (Bloomberg media family of sites)";
				status obsolete;
			}

			enum "businessweekly" {
				opd:help "Weekly financial news, delivered every Thursday, providing industry information, enterprise Interviews, enterprise stories, financial news and other content";
				status obsolete;
			}

			enum "buzzfeed" {
				opd:help "International news webportal";
				status obsolete;
			}

			enum "buzzhand" {
				opd:help "Bermudan news portal";
				status obsolete;
			}

			enum "buzznet" {
				opd:help "Social media website owned by an American company, Spinmedia";
				status obsolete;
			}

			enum "buzzsenegal" {
				opd:help "Viral news and videos website from Senegal";
				status obsolete;
			}

			enum "bwiza" {
				opd:help "Local news portal in Rwanda";
				status obsolete;
			}

			enum "bxml" {
				opd:help "The WAP Binary XML protocol defines an encoding scheme for the binary data used in WAP environments";
				status obsolete;
			}

			enum "bypassthat" {
				opd:help "Free web proxy";
				status obsolete;
			}

			enum "caak" {
				opd:help "Mongolian news portal";
				status obsolete;
			}

			enum "caasimadda" {
				opd:help "News webportal in Somalia";
				status obsolete;
			}

			enum "caf" {
				opd:help "French National Fund for Family Allowances (Caisse d'allocation familiale)";
				status obsolete;
			}

			enum "cafemom" {
				opd:help "Social network based in New York City targeting mothers";
				status obsolete;
			}

			enum "caliente" {
				opd:help "Famous gambling website, featuring sports and online games, in Mexico";
				status obsolete;
			}

			enum "cam4" {
				opd:help "Adult-webcam video website";
				status obsolete;
			}

			enum "cameroon_info" {
				opd:help "Cameroonian news portal";
				status obsolete;
			}

			enum "campfire" {
				opd:help "This classifies the HTTP traffic to the host campfirenow.com";
				status obsolete;
			}

			enum "camzap" {
				opd:help "(Deprecated) Classifies HTTP traffic to the host camzap.com, which hosted multi-channel webcam chat rooms for strangers to chat simultaneously";
				status obsolete;
			}

			enum "canalrcn" {
				opd:help "Colombian private RCN Television website";
				status obsolete;
			}

			enum "candy_crush_saga" {
				opd:help "Candy Crush Saga is a mobile puzzle game edited by King Entertainment";
				status obsolete;
			}

			enum "capitalone" {
				opd:help "American Credit card company and bank";
				status obsolete;
			}

			enum "carbonite" {
				opd:help "Carbonite is a service that manages online backups";
				status obsolete;
			}

			enum "care2" {
				opd:help "Social network for citizens and activists";
				status obsolete;
			}

			enum "cari" {
				opd:help "Popular portal providing information about Malaysia";
				status obsolete;
			}

			enum "carsales" {
				opd:help "Australian online portal to search for new and used cars for sale";
				status obsolete;
			}

			enum "cartoonnetwork" {
				opd:help "Websites of an American TV channel for children";
				status obsolete;
			}

			enum "cas" {
				opd:help "Slovak news portal";
				status obsolete;
			}

			enum "catchoftheday" {
				opd:help "Online shopping site in Australia";
				status obsolete;
			}

			enum "caymannewsservice" {
				opd:help "Cayman Islands news website";
				status obsolete;
			}

			enum "cbs_video" {
				opd:help "CBS Video is a site which streams movies, TV series, etc";
				status obsolete;
			}

			enum "cbt" {
				opd:help "The cbt protocol (Core-based trees) is found over the IP layer (IANA protocol number: 7)";
				status obsolete;
			}

			enum "ccp" {
				opd:help "The Compression Control Protocol (CCP) is responsible for configuring data compression algorithms on a point-to-point link";
				status obsolete;
			}

			enum "ccproxy" {
				opd:help "CCProxy is a windows based software proxy";
				status obsolete;
			}

			enum "cctv_vod" {
				opd:help "VodCCTV provides a web on-line video and video on demand client for the CCTV Chinese television network";
				status obsolete;
			}

			enum "cdiscount" {
				opd:help "Major French e-commerce website";
				status obsolete;
			}

			enum "cdm" {
				opd:help "Montenegrin news portal";
				status obsolete;
			}

			enum "cdnetworks" {
				opd:help "CDNetworks is a global Content Delivery Network";
				status obsolete;
			}

			enum "cedexis" {
				opd:help "Cedexis provides analytics solutions for CDN and Clouds services";
				status obsolete;
			}

			enum "cellufun" {
				opd:help "Cellufun, also known as Tylted, is a social gaming community accessible from any mobile device, and developer of Java-based games";
				status obsolete;
			}

			enum "central_torrent" {
				opd:help "BitTorrent tracker search engine";
				status obsolete;
			}

			enum "centrum_cz" {
				opd:help "Czech web portal";
				status obsolete;
			}

			enum "centrum_sk" {
				opd:help "Slovakian web portal";
				status obsolete;
			}

			enum "cft" {
				opd:help "CFT (Cross File Transfer) is a file transfer software developed by Axway";
				status obsolete;
			}

			enum "cftp" {
				opd:help "The cftp protocol (CFTP) is found over the IP layer (IANA protocol number: 62)";
				status obsolete;
			}

			enum "cgiproxy" {
				opd:help "CGIProxy is a proxy software package";
				status obsolete;
			}

			enum "cgmp" {
				opd:help "Cisco Group Management Protocol (CGMP) limits the forwarding of IP multicast packets to only those ports associated with IP multicast clients";
				status obsolete;
			}

			enum "champion_football" {
				opd:help "Mobile game";
				status obsolete;
			}

			enum "channel4" {
				opd:help "British TV channel Channel4's website";
				status obsolete;
			}

			enum "channelmyanmar" {
				opd:help "Burmese movie download platform and web blog service";
				status obsolete;
			}

			enum "chaos" {
				opd:help "The chaos protocol (Chaos) is found over the IP layer (IANA protocol number: 16)";
				status obsolete;
			}

			enum "chap" {
				opd:help "The CHAP protocol is used to verify the identity of a peer on a point-to-point link";
				status obsolete;
			}

			enum "chat_on" {
				opd:help "(Deprecated) ChatON was a global mobile communication service introduced by Samsung Electronics";
				status obsolete;
			}

			enum "chatroulette" {
				opd:help "Chatroulette is an online video chat website";
				status obsolete;
			}

			enum "cheetah_mobile" {
				opd:help "Cheetah Mobile is a mobile application editor (launcher, tools, etc.)";
				status obsolete;
			}

			enum "china_airlines" {
				opd:help "China-airlines booking site";
				status obsolete;
			}

			enum "china_youth_league" {
				opd:help "Chinese news web portal";
				status obsolete;
			}

			enum "chinacom" {
				opd:help "Chinese news website";
				status obsolete;
			}

			enum "chinacomcn" {
				opd:help "Chinese news website";
				status obsolete;
			}

			enum "chinadaily" {
				opd:help "Chinese website providing articles on topics such as communication, lifestyle, work, money, health or technology";
				status obsolete;
			}

			enum "chinanews" {
				opd:help "Chinese news portal";
				status obsolete;
			}

			enum "chinaren" {
				opd:help "Chinese social networking website for former classmates";
				status obsolete;
			}

			enum "chinatimes" {
				opd:help "One of Taiwan top news portal";
				status obsolete;
			}

			enum "chinaz" {
				opd:help "Chinese news website";
				status obsolete;
			}

			enum "chosun" {
				opd:help "News websites and web services belonging to a famous newspaper in South Korea, Chosun Ilbo";
				status obsolete;
			}

			enum "chosun_daily" {
				opd:help "(Deprecated) News website belonging to a famous newspaper in South Korea, Chosun Ilbo";
				status obsolete;
			}

			enum "chouftv" {
				opd:help "Moroccan TV portal with live broadcasts and VoD";
				status obsolete;
			}

			enum "chrome_remote_desktop" {
				opd:help "This signature classifies chrome remote desktop based on DNS caching and SSL common name on PC as well as on Mobile";
				status obsolete;
			}

			enum "chrome_update" {
				opd:help "Chrome Update is the protocol for the updates of the Google chrome browser";
				status obsolete;
			}

			enum "cibercuba" {
				opd:help "News website in Cuba";
				status obsolete;
			}

			enum "cinemageddon" {
				opd:help "(Deprecated) BitTorrent tracker search engine";
				status obsolete;
			}

			enum "cip" {
				opd:help "The Common Industrial Protocol (CIP) is an industrial protocol for industrial automation applications";
				status obsolete;
			}

			enum "citizentv" {
				opd:help "Kenyan news website, including top stories, politics, business, sports, and lifestyle";
				status obsolete;
			}

			enum "citrix_online" {
				opd:help "On-line collaboration suite for small businesses";
				status obsolete;
			}

			enum "citrix_pvs" {
				opd:help "Citrix PVS provides an infrastructure to stream shared Xen Virtual Machine images (vDisk) to hosts";
				status obsolete;
			}

			enum "cj_mall" {
				opd:help "South Korean e-commerce website belonging to the CJ Corporation";
				status obsolete;
			}

			enum "ck101" {
				opd:help "ck101 is one of the major forum sites in Taiwan";
				status obsolete;
			}

			enum "clarin" {
				opd:help "Argentinian news portal";
				status obsolete;
			}

			enum "clash_of_clans" {
				opd:help "Clash of Clans is a free-to-play mobile MMO strategy video game developed by Supercell";
				status obsolete;
			}

			enum "clasificadosonline" {
				opd:help "Puerto Rican classified ads";
				status obsolete;
			}

			enum "classmates" {
				opd:help "American social network based on finding high-school alumni";
				status obsolete;
			}

			enum "clearcase" {
				opd:help "ClearCase is a source control / configuration management tool from IBM's \"Rational\" division";
				status obsolete;
			}

			enum "clearspace" {
				opd:help "Enterprise collaboration and knowledge management platform";
				status obsolete;
			}

			enum "clicanoo" {
				opd:help "Reunion island news portal";
				status obsolete;
			}

			enum "clicktale" {
				opd:help "Clicktale is a customer experience analytics platform";
				status obsolete;
			}

			enum "clickyab" {
				opd:help "Iranian web advertising services portal";
				status obsolete;
			}

			enum "clien" {
				opd:help "Southern Korean website for exchanges and posts about several topics";
				status obsolete;
			}

			enum "clip" {
				opd:help "Vietnamese multimedia streaming website";
				status obsolete;
			}

			enum "clip2net" {
				opd:help "Website which allows users to capture and share images online";
				status obsolete;
			}

			enum "cloob" {
				opd:help "Persian-speaking social network popular in Iran";
				status obsolete;
			}

			enum "cloudflare" {
				opd:help "CloudFlare CDN is a content delivery network with advanced security and analytics features";
				status obsolete;
			}

			enum "cloudinary" {
				opd:help "Cloudinary is a cloud service";
				status obsolete;
			}

			enum "cloudme" {
				opd:help "Free on-line file storage service";
				status obsolete;
			}

			enum "clubbox" {
				opd:help "Korean file sharing website that requires installing a P2P client called zmlauncher.exe";
				status obsolete;
			}

			enum "clubic" {
				opd:help "French High-tech news website";
				status obsolete;
			}

			enum "clumsy_ninja" {
				opd:help "Mobile game";
				status obsolete;
			}

			enum "cnet" {
				opd:help "CNET is a media website publishing news, reviews, blog posts and videos about technology";
				status obsolete;
			}

			enum "cnet_tv" {
				opd:help "CNET Video is a web television network";
				status obsolete;
			}

			enum "cnm" {
				opd:help "Web portal offering the latest breaking news from Maldives";
				status obsolete;
			}

			enum "cnn" {
				opd:help "CNN is an international TV network, broadcasting news to the web and to mobile device applications";
				status obsolete;
			}

			enum "cntv" {
				opd:help "Chinese Central Television and China Network Television website";
				status obsolete;
			}

			enum "cnyes" {
				opd:help "cnYES.com is a financial portal among the Chinese online professionals";
				status obsolete;
			}

			enum "cnzz" {
				opd:help "Website that offers web-services and statistics to the Chinese-speaking users";
				status obsolete;
			}

			enum "coap" {
				opd:help "CoAP (Constrained Application Protocol) is a specialized web transfer protocol for use with constrained nodes and constrained networks in the Internet of Things";
				status obsolete;
			}

			enum "coccoc" {
				opd:help "Vietnamese search engine";
				status obsolete;
			}

			enum "cocolog_nifty" {
				opd:help "Japanese blog website";
				status obsolete;
			}

			enum "college_blender" {
				opd:help "American website that provides resources and articles about College life";
				status obsolete;
			}

			enum "comcast" {
				opd:help "Comcast Corporation is an American global mass media conglomerate and is a large broadcasting and cable television company";
				status obsolete;
			}

			enum "comm" {
				opd:help "COMM is a VoIP and Instant messaging application for mobile phones commonly used in Japan";
				status obsolete;
			}

			enum "commbank" {
				opd:help "Australian online personal banking, business solutions, institutional banking, company information, etc";
				status obsolete;
			}

			enum "commentcamarche" {
				opd:help "CommentCaMarche.net is a French website providing technical explanations as well as forums";
				status obsolete;
			}

			enum "comp" {
				opd:help "COMP protocol is used for data compression over PPP";
				status obsolete;
			}

			enum "compaq_peer" {
				opd:help "The compaq_peer protocol (Compaq Peer Protocol) is found over the IP layer (IANA protocol number: 110)";
				status obsolete;
			}

			enum "concur" {
				opd:help "SaaS business management solutions owned by SAP, which provides expense, travel and invoice management";
				status obsolete;
			}

			enum "conduit" {
				opd:help "Conduit provides services for websites audience increase";
				status obsolete;
			}

			enum "constantcontact" {
				opd:help "Constant Contact is an online marketing company serving small businesses, nonprofit organizations, and membership associations";
				status obsolete;
			}

			enum "contentabc" {
				opd:help "Content Delivery Network used by youporn, redtube and tube8 websites";
				status obsolete;
			}

			enum "conversant" {
				opd:help "Conversant is an online advertising company";
				status obsolete;
			}

			enum "conviva" {
				opd:help "Conviva is a video streaming optimization and analytics solution provider for audio/video content web services";
				status obsolete;
			}

			enum "coralcdn_user" {
				opd:help "(Deprecated) Coral Content Distribution Network (also known as CoralCDN) provided free and open content distribution through peer-to-peer networking";
				status obsolete;
			}

			enum "corotos" {
				opd:help "Classified ads website in Dominican Republic";
				status obsolete;
			}

			enum "corriere" {
				opd:help "Global news website from Italy";
				status obsolete;
			}

			enum "cotp" {
				opd:help "COTP (Connection Oriented Transport Protocol) is a protocol ensuring the transport service in the OSI model";
				status obsolete;
			}

			enum "couch_surfing" {
				opd:help "Social and traveling network that relies on users' hospitality";
				status obsolete;
			}

			enum "coupang" {
				opd:help "Korean e-commerce website";
				status obsolete;
			}

			enum "cpasbien" {
				opd:help "Famous French torrent website";
				status obsolete;
			}

			enum "cphb" {
				opd:help "The cphb protocol (Computer Protocol Heart Beat) is found over the IP layer (IANA protocol number: 73)";
				status obsolete;
			}

			enum "cpmstar" {
				opd:help "Advertising platform for videogames";
				status obsolete;
			}

			enum "cpnx" {
				opd:help "The cpnx protocol (Computer Protocol Network Executive) is found over the IP layer (IANA protocol number: 72)";
				status obsolete;
			}

			enum "crackle" {
				opd:help "Crackle is an entertainment network and studio that distributes free movies, television shows and original programming";
				status obsolete;
			}

			enum "craigslist" {
				opd:help "Online classified ads mostly used in the US and Canada";
				status obsolete;
			}

			enum "crashlytics" {
				opd:help "Crashlytics is a mobile company building crash reporting for iOS and Android";
				status obsolete;
			}

			enum "crazysaloon" {
				opd:help "(Deprecated) BitTorrent tracker search engine";
				status obsolete;
			}

			enum "crhoy" {
				opd:help "Costa Rican news portal";
				status obsolete;
			}

			enum "criteo" {
				opd:help "Criteo is a personalized retargeting company";
				status obsolete;
			}

			enum "crittercism" {
				opd:help "Crittercism is a mobile application for performance management";
				status obsolete;
			}

			enum "crnobelo" {
				opd:help "Macedonian news portal";
				status obsolete;
			}

			enum "crocko" {
				opd:help "CROCKOTec is a Direct Download (DDL file sharing website)";
				status obsolete;
			}

			enum "crtp" {
				opd:help "The crtp protocol (Combat Radio Transport Protocol) is found over the IP layer (IANA protocol number: 126)";
				status obsolete;
			}

			enum "crudp" {
				opd:help "The crudp protocol (Combat Radio User Datagram) is found over the IP layer (IANA protocol number: 127)";
				status obsolete;
			}

			enum "cryptoheaven" {
				opd:help "Secure email and online file storage service";
				status obsolete;
			}

			enum "cryptospout" {
				opd:help "Free web service where users can collect free cryptocoins for some of the largest cryptocurrencies available";
				status obsolete;
			}

			enum "crystalbet" {
				opd:help "Georgian online betting and gaming platform";
				status obsolete;
			}

			enum "csdn" {
				opd:help "A large application-developer's network in China";
				status obsolete;
			}

			enum "cstrike" {
				opd:help "Cstrike is a protocol used by CounterStrike game, by Steam";
				status obsolete;
			}

			enum "ctrip" {
				opd:help "Travel Destination Guide, online booking of hotels, flights and holiday";
				status obsolete;
			}

			enum "cubadebate" {
				opd:help "Cuban news portal";
				status obsolete;
			}

			enum "cups" {
				opd:help "The Common Unix Printer System (CUPS) protocol is a cross-platform printing solution for UNIX environments";
				status obsolete;
			}

			enum "curapelanatureza" {
				opd:help "Blog dedicated to health and wellness, popular in Brazil";
				status obsolete;
			}

			enum "curse" {
				opd:help "Curse is an on-line game portal and a game add-on and modifications management application";
				status obsolete;
			}

			enum "cuteyhoneyflash" {
				opd:help "(Deprecated) BitTorrent tracker search engine";
				status obsolete;
			}

			enum "cv_online" {
				opd:help "Estonian job hunting website";
				status obsolete;
			}

			enum "cvbankas" {
				opd:help "Lithuanian job hunting website";
				status obsolete;
			}

			enum "cvs" {
				opd:help "The Concurrent Versions System keeps track of all work and all changes in a set of files, typically the implementation of a software project, and allows several developers to collaborate";
				status obsolete;
			}

			enum "cwseychelles" {
				opd:help "Internet services provider in the Seychelles, providing access and hosting services";
				status obsolete;
			}

			enum "cyber12" {
				opd:help "BitTorrent tracker search engine";
				status obsolete;
			}

			enum "cyberctm" {
				opd:help "Chinese news portal";
				status obsolete;
			}

			enum "cyworld" {
				opd:help "CYworld is a South Korean social network service which belongs to nate.com";
				status obsolete;
			}

			enum "da7ye" {
				opd:help "News website in Lebanon";
				status obsolete;
			}

			enum "dagbladet" {
				opd:help "Norwegian news portal";
				status obsolete;
			}

			enum "daikynguyen" {
				opd:help "Global news web portal located in Vietnam";
				status obsolete;
			}

			enum "daily_booth" {
				opd:help "(Deprecated) Classifies the HTTP traffic to the host dailybooth.com";
				status obsolete;
			}

			enum "daily_pakistan" {
				opd:help "Daily newspaper web portal from Pakistan";
				status obsolete;
			}

			enum "daily_strength" {
				opd:help "American social network that relies on support groups";
				status obsolete;
			}

			enum "dailymail" {
				opd:help "Daily Mail is a famous daily news website, and dedicated mobile application, from UK";
				status obsolete;
			}

			enum "dailymotion" {
				opd:help "Dailymotion is a website where users can send or watch videos";
				status obsolete;
			}

			enum "dakaractu" {
				opd:help "Senegalese news portal";
				status obsolete;
			}

			enum "dameware" {
				opd:help "DameWare is a remote access software for end user support and systems troubleshooting";
				status obsolete;
			}

			enum "dangdang" {
				opd:help "Books, film and television productions, and digital products shopping site";
				status obsolete;
			}

			enum "danishbits" {
				opd:help "BitTorrent tracker search engine";
				status obsolete;
			}

			enum "dantri" {
				opd:help "Vietnamese news portal";
				status obsolete;
			}

			enum "dap_news" {
				opd:help "Cambodian news portal";
				status obsolete;
			}

			enum "daraz" {
				opd:help "Online shopping mall in Pakistan";
				status obsolete;
			}

			enum "data_hu" {
				opd:help "Classifies web browsing on the data.hu Direct DownLoad links service";
				status obsolete;
			}

			enum "daum" {
				opd:help "Korean web portal that features integrated web-messaging services";
				status obsolete;
			}

			enum "daummail" {
				opd:help "Webmail for daum.net";
				status obsolete;
			}

			enum "davidov" {
				opd:help "This classifies the HTTP traffic to the host davidov.do.am";
				status obsolete;
			}

			enum "day" {
				opd:help "Azerbaijani news portal";
				status obsolete;
			}

			enum "db2" {
				opd:help "DB2 is a relational model database server from IBM which has its roots in the early 1980s";
				status obsolete;
			}

			enum "dba" {
				opd:help "Danish classified ads website";
				status obsolete;
			}

			enum "dbs" {
				opd:help "Singaporian online banking website";
				status obsolete;
			}

			enum "dccp" {
				opd:help "The dccp protocol (Datagram Congestion Control Protocol) is found over the IP layer (IANA protocol number: 33)";
				status obsolete;
			}

			enum "dcerpc" {
				opd:help "The DCERPC protocol is an RPC implementation used in Distributed Computing Environments";
				status obsolete;
			}

			enum "dcinside" {
				opd:help "Information portal ( www.dcinside.com )";
				status obsolete;
			}

			enum "dcn_meas" {
				opd:help "The dcn_meas protocol (DCN Measurement Subsystems) is found over the IP layer (IANA protocol number: 19)";
				status obsolete;
			}

			enum "ddp" {
				opd:help "The ddp protocol (Datagram Delivery Protocol) is found over the IP layer (IANA protocol number: 37)";
				status obsolete;
			}

			enum "ddx" {
				opd:help "The ddx protocol (D-II Data Exchange (DDX)) is found over the IP layer (IANA protocol number: 116)";
				status obsolete;
			}

			enum "dealdey" {
				opd:help "Online shopping site in Nigeria";
				status obsolete;
			}

			enum "dealfish" {
				opd:help "(Deprecated) Thai classified ads";
				status obsolete;
			}

			enum "debian" {
				opd:help "This classifies the traffic on debian.org";
				status obsolete;
			}

			enum "debian_update" {
				opd:help "Update protocol of APT, the Debian/Ubuntu packet manager";
				status obsolete;
			}

			enum "dec" {
				opd:help "DEC is a Digital Equipment Corporation's proprietary network protocol";
				status obsolete;
			}

			enum "decayenne" {
				opd:help "This classifies the HTTP traffic to the host decayenne.com";
				status obsolete;
			}

			enum "deepseek" {
				opd:help "BitTorrent tracker search engine";
				status obsolete;
			}

			enum "deer_hunter_2014" {
				opd:help "Mobile game";
				status obsolete;
			}

			enum "deezer" {
				opd:help "Deezer is a French music streaming service which can run in web browsers and mobile applications";
				status obsolete;
			}

			enum "defimedia" {
				opd:help "Mauritian news portal";
				status obsolete;
			}

			enum "delfi" {
				opd:help "Estonian news portal, also accessible from Latvia and Lithuania";
				status obsolete;
			}

			enum "delicious" {
				opd:help "Delicious (formerly del.icio.us, pronounced \"delicious\") is a social bookmarking web service for storing, sharing, and discovering web bookmarks";
				status obsolete;
			}

			enum "delta_search" {
				opd:help "Browser toolbar search engine";
				status obsolete;
			}

			enum "depositfiles" {
				opd:help "DepositFiles is a file sharing web service";
				status obsolete;
			}

			enum "derstandard" {
				opd:help "Austrian news portal";
				status obsolete;
			}

			enum "deskaway" {
				opd:help "DeskAway is a web-based team and project management software that makes it easy to organize, manage and track projects from a central location";
				status obsolete;
			}

			enum "destiny" {
				opd:help "Destiny is a first-person shooter video game developed by Bungie and published by Activision";
				status obsolete;
			}

			enum "detik" {
				opd:help "This classifies the HTTP and SSL traffic to the host detik.com";
				status obsolete;
			}

			enum "detiknews" {
				opd:help "This classifies the HTTP traffic to the hosts detiknews.com and news.detik.com";
				status obsolete;
			}

			enum "deviant_art" {
				opd:help "This classifies the HTTP traffic to the host deviantart.com";
				status obsolete;
			}

			enum "dfs" {
				opd:help "The dfs protocol (Any distributed file system) is found over the IP layer (IANA protocol number: 68)";
				status obsolete;
			}

			enum "dgp" {
				opd:help "The dgp protocol (Dissimilar Gateway Protocol) is found over the IP layer (IANA protocol number: 86)";
				status obsolete;
			}

			enum "dhcp" {
				opd:help "The DHCP protocol is used to configure automatically the network parameters of a station";
				status obsolete;
			}

			enum "dhcp6" {
				opd:help "The DHCPv6 protocol is used to automatically configure the network parameters of a station in an IPv6 network";
				status obsolete;
			}

			enum "diameter" {
				opd:help "Diameter is an AAA (authentication, authorization and accounting) protocol for computer networks and an alternative to RADIUS";
				status obsolete;
			}

			enum "dianping" {
				opd:help "Chinese group buying website selling vouchers on local services and entertainment";
				status obsolete;
			}

			enum "dict" {
				opd:help "The DICT protocol is a TCP transaction based query/response protocol that enables a client to access dictionary definitions from a set of natural language dictionary databases";
				status obsolete;
			}

			enum "digg" {
				opd:help "This classifies the HTTP and SSL traffic to the host digg.com";
				status obsolete;
			}

			enum "digikala" {
				opd:help "Iranian electronics and tech review website";
				status obsolete;
			}

			enum "digitalriver" {
				opd:help "Digital River is a public company that provides internet commerce services";
				status obsolete;
			}

			enum "digitalverse" {
				opd:help "This classifies the HTTP traffic to the host digitalverse.org";
				status obsolete;
			}

			enum "diino" {
				opd:help "Diino is an online drive allowing users to upload and share their files";
				status obsolete;
			}

			enum "dimp" {
				opd:help "DIMP is a Webmail protocol";
				status obsolete;
			}

			enum "diodeo" {
				opd:help "Information portal ( www.diodeo.com )";
				status obsolete;
			}

			enum "diop" {
				opd:help "DIOP is a GIOP implementation over UDP which aims to be more efficient than the TCP one";
				status obsolete;
			}

			enum "diply" {
				opd:help "Entertainment website powered by user's posts";
				status obsolete;
			}

			enum "dir" {
				opd:help "Bulgarian news portal";
				status obsolete;
			}

			enum "directconnect" {
				opd:help "DirectConnect is a peer-to-peer protocol";
				status obsolete;
			}

			enum "directdownloadlinks" {
				opd:help "(Deprecated) Direct download link is a term used within the Internet-based file sharing community";
				status obsolete;
			}

			enum "directrev" {
				opd:help "DirectREV Media Delivery Platform is a real-time digital ad marketplace that connects publishers with agencies, ad networks and third-party technology providers";
				status obsolete;
			}

			enum "directv" {
				opd:help "DirecTV is a satellite television service";
				status obsolete;
			}

			enum "diretube" {
				opd:help "Ethiopian media website";
				status obsolete;
			}

			enum "disaboom" {
				opd:help "This classifies the HTTP traffic to the host disaboom.com";
				status obsolete;
			}

			enum "discuss" {
				opd:help "Hong Kongese forum about media and lifestyle";
				status obsolete;
			}

			enum "disney_channel" {
				opd:help "Disney Channel website";
				status obsolete;
			}

			enum "disney_junior" {
				opd:help "This is the Disney Channel website for kids between 3 to 7 years";
				status obsolete;
			}

			enum "disney_xd" {
				opd:help "Disney XD Channel VoD website";
				status obsolete;
			}

			enum "distcc" {
				opd:help "Distributed C Compiler protocol";
				status obsolete;
			}

			enum "divar" {
				opd:help "Classified ads platform in Iran";
				status obsolete;
			}

			enum "divshare" {
				opd:help "This classifies the HTTP traffic to the host divshare.com";
				status obsolete;
			}

			enum "dmm_co" {
				opd:help "Japanese adult videos website";
				status obsolete;
			}

			enum "dnevnik" {
				opd:help "News webportal from Croatia";
				status obsolete;
			}

			enum "dnp3" {
				opd:help "DNP3 (Distributed Network Protocol) is a set of protocols used between components in process automation systems (SCADA)";
				status obsolete;
			}

			enum "dns" {
				opd:help "The DNS protocol is used to translate internet names into IP addresses and vice versa";
				status obsolete;
			}

			enum "dns2tcp" {
				opd:help "Dns2tcp is a solution which provides tunneling through the standard DNS protocol";
				status obsolete;
			}

			enum "dnshop" {
				opd:help "This classifies the traffic to the host dnshop.com";
				status obsolete;
			}

			enum "dnxlive" {
				opd:help "Dnx Live is a live webcam platform";
				status obsolete;
			}

			enum "docstoc" {
				opd:help "This classifies the HTTP traffic to the hosts docstoccdn.com and docstoc.com";
				status obsolete;
			}

			enum "docusign" {
				opd:help "Company providing electronic signature technology and digital transaction services for facilitating electronic exchanges of contracts and signed documents";
				status obsolete;
			}

			enum "doisongphapluat" {
				opd:help "Vietnamese news portal";
				status obsolete;
			}

			enum "dol2day" {
				opd:help "This classifies the HTTP traffic to the host dol2day.com";
				status obsolete;
			}

			enum "domain" {
				opd:help "Australian site for residential/commercial/rural property solutions";
				status obsolete;
			}

			enum "donedeal" {
				opd:help "Irish classified ads website";
				status obsolete;
			}

			enum "donga" {
				opd:help "This classifies the HTTP traffic to the host donga.com";
				status obsolete;
			}

			enum "dontstayin" {
				opd:help "This classifies the HTTP traffic to the host dontstayin.com";
				status obsolete;
			}

			enum "doodle_jump" {
				opd:help "Mobile game developed by Lima Sky LLC";
				status obsolete;
			}

			enum "doorblog" {
				opd:help "This classifies the HTTP traffic to the host doorblog.jp";
				status obsolete;
			}

			enum "dorgio" {
				opd:help "Mongolian news portal";
				status obsolete;
			}

			enum "dostor" {
				opd:help "News web portal popular in Egypt";
				status obsolete;
			}

			enum "douban" {
				opd:help "This classifies the HTTP traffic to the host douban.com";
				status obsolete;
			}

			enum "doubleverify" {
				opd:help "DoubleVerify provides online media verification and campaign effectiveness solutions for marketers, advertisers and digital publishers";
				status obsolete;
			}

			enum "douyu" {
				opd:help "Douyu is a live gaming video site";
				status obsolete;
			}

			enum "dr" {
				opd:help "Danish news and content portal";
				status obsolete;
			}

			enum "draugas" {
				opd:help "Lithuanian web portal";
				status obsolete;
			}

			enum "draugiem" {
				opd:help "This classifies the HTTP and SSL traffic to the host draugiem.lv";
				status obsolete;
			}

			enum "drda" {
				opd:help "DRDA is a protocol for carrying out SQL queries and commands";
				status obsolete;
			}

			enum "dreamora" {
				opd:help "BitTorrent tracker search engine";
				status obsolete;
			}

			enum "dreamwiz" {
				opd:help "This classifies the HTTP traffic to the host dreamwiz.com";
				status obsolete;
			}

			enum "dropbox" {
				opd:help "Dropbox is a free in-the-cloud file storage and synchronization service providing both web and smart application interfaces";
				status obsolete;
			}

			enum "dropbox_download" {
				opd:help "File downloading service of Dropbox";
				status obsolete;
			}

			enum "dropbox_upload" {
				opd:help "File uploading service of Dropbox";
				status obsolete;
			}

			enum "dropshots" {
				opd:help "Website for sharing photos, videos, etc";
				status obsolete;
			}

			enum "druknet" {
				opd:help "Buthan Telecom website";
				status obsolete;
			}

			enum "drupal" {
				opd:help "This classifies the HTTP traffic to the host drupal.org";
				status obsolete;
			}

			enum "dsi" {
				opd:help "The Data Stream Interface (DSI) is a session layer used to carry Apple Filing Protocol traffic over Transmission Control Protocol (TCP)";
				status obsolete;
			}

			enum "dsr" {
				opd:help "The dsr protocol (Dynamic Source Routing Protocol) is found over the IP layer (IANA protocol number: 48)";
				status obsolete;
			}

			enum "dstv" {
				opd:help "Program synopsis and channel information for South Africa satellite network";
				status obsolete;
			}

			enum "dtls" {
				opd:help "DTLS stands for Datagram Transport Layer Security protocol";
				status obsolete;
			}

			enum "dtp" {
				opd:help "DTP (Dynamic Trunk Protocol) is a proprietary networking protocol developed by Cisco Systems for the purpose of negotiating trunking on a link between two VLAN-aware switches";
				status obsolete;
			}

			enum "dubizzle" {
				opd:help "Dubizzle is your free classifieds website to buy, sell and find anything in your local community";
				status obsolete;
			}

			enum "duodecad_its" {
				opd:help "Duodecad IT Services Luxembourg is developing and operating multimedia services";
				status obsolete;
			}

			enum "duowan" {
				opd:help "Chinese online game media";
				status obsolete;
			}

			enum "dv" {
				opd:help "Icelandic news portal";
				status obsolete;
			}

			enum "dwarozh" {
				opd:help "Iraqi news and live radio webportal";
				status obsolete;
			}

			enum "dwtonline" {
				opd:help "Daily Surinamese newspaper web portal";
				status obsolete;
			}

			enum "dwu" {
				opd:help "Website of a Catholic university in Papua New Guinea";
				status obsolete;
			}

			enum "dynamicintranet" {
				opd:help "This classifies the HTTP traffic to the host dynamicintranet.com";
				status obsolete;
			}

			enum "e_boks" {
				opd:help "Free online secured digital mailbox service for individuals and companies, popular in Denmark";
				status obsolete;
			}

			enum "earthcam" {
				opd:help "This classifies the HTTP traffic to the host earthcam.com";
				status obsolete;
			}

			enum "earthlinktele" {
				opd:help "Internet, cloud, enterprise network and cloud services provider";
				status obsolete;
			}

			enum "eastmoney" {
				opd:help "Chinese financial media, providing comprehensive financial news and financial market information, covering stocks, finance, securities, finance, market, funds, Hong Kong stocks, foreign exchange, futures, bonds, insurance, banking";
				status obsolete;
			}

			enum "easytravel" {
				opd:help "Taiwanese travel booking agency";
				status obsolete;
			}

			enum "ebay" {
				opd:help "Ebay is a famous online auction and shopping website";
				status obsolete;
			}

			enum "ebay_classifieds" {
				opd:help "Ebay related website specialized in classified ads per geographic region";
				status obsolete;
			}

			enum "ebuddy" {
				opd:help "eBuddy is a web and mobile messenger which supports various instant messaging";
				status obsolete;
			}

			enum "ecaytrade" {
				opd:help "Classified ads web portal from Cayman Islands";
				status obsolete;
			}

			enum "echo" {
				opd:help "The echo service simply sends back to the originating source any data it receives";
				status obsolete;
			}

			enum "echoroukonline" {
				opd:help "Algerian news portal";
				status obsolete;
			}

			enum "ecuavisa" {
				opd:help "Ecuadorian TV channel website";
				status obsolete;
			}

			enum "edgecast" {
				opd:help "Edgecast is a file streaming solution provider for audio/video content web services";
				status obsolete;
			}

			enum "edonkey" {
				opd:help "Edonkey is a peer-to-peer protocol";
				status obsolete;
			}

			enum "edu365" {
				opd:help "Schools management information system provider";
				status obsolete;
			}

			enum "educarriere" {
				opd:help "Ivory Coast Job portal";
				status obsolete;
			}

			enum "egloos" {
				opd:help "Egloos is a South Korean blog hosting website";
				status obsolete;
			}

			enum "egnyte" {
				opd:help "Enterprise online file sharing";
				status obsolete;
			}

			enum "egp" {
				opd:help "The egp protocol (Exterior Gateway Protocol) is found over the IP layer (IANA protocol number: 8)";
				status obsolete;
			}

			enum "eigrp" {
				opd:help "The Enhanced Interior Gateway Routing Protocol (EIGRP) is an improved version of its predecessor IGRP, a Cisco proprietary protocol";
				status obsolete;
			}

			enum "ekantipur" {
				opd:help "Nepalese news portal";
				status obsolete;
			}

			enum "eksisozluk" {
				opd:help "Turkish forum on various topics";
				status obsolete;
			}

			enum "ekskluziva" {
				opd:help "Bosnian showbiz related news website";
				status obsolete;
			}

			enum "ekstrabladet" {
				opd:help "Danish news portal";
				status obsolete;
			}

			enum "el_balad" {
				opd:help "Egyptian news portal";
				status obsolete;
			}

			enum "el_nacional" {
				opd:help "Famous Venezuelan newspaper web portal";
				status obsolete;
			}

			enum "elasticsearch" {
				opd:help "Elasticsearch is a search engine";
				status obsolete;
			}

			enum "elblog" {
				opd:help "El Salvadorian news portal";
				status obsolete;
			}

			enum "elbotola" {
				opd:help "Moroccan football-related news and social website";
				status obsolete;
			}

			enum "elcat" {
				opd:help "Kyrgyzstanese internet service provider";
				status obsolete;
			}

			enum "elcomercio" {
				opd:help "Peruvian news portal";
				status obsolete;
			}

			enum "eldeber" {
				opd:help "Bolivian news portal";
				status obsolete;
			}

			enum "elfagr" {
				opd:help "Egyptian news portal";
				status obsolete;
			}

			enum "elftown" {
				opd:help "This classifies the HTTP traffic to the host elftown.com";
				status obsolete;
			}

			enum "elhawd" {
				opd:help "News web portal dedicated to Africa news, popular in Senegal and Mauritania";
				status obsolete;
			}

			enum "elheddaf" {
				opd:help "Algerian sports new portal";
				status obsolete;
			}

			enum "elheraldo" {
				opd:help "Honduran news portal";
				status obsolete;
			}

			enum "elhourriya" {
				opd:help "Mauritanian news portal";
				status obsolete;
			}

			enum "elkhadra" {
				opd:help "Business, Money and Financial news website popular in Algeria";
				status obsolete;
			}

			enum "elle_tw" {
				opd:help "Taiwanese portal Beauty, style trends, editor's picks, shopping, astrology, reader forums and supplemental content from the print publication";
				status obsolete;
			}

			enum "elluminate" {
				opd:help "Rent virtual rooms where people can hold classes and meetings";
				status obsolete;
			}

			enum "elmogaz" {
				opd:help "Egyptian news portal";
				status obsolete;
			}

			enum "elmundo" {
				opd:help "Spanish news portal";
				status obsolete;
			}

			enum "elnashra" {
				opd:help "Lebanese news portal";
				status obsolete;
			}

			enum "elnoticiero" {
				opd:help "Ecuadorian general news website owned by TC Television";
				status obsolete;
			}

			enum "elnuevodia" {
				opd:help "Puerto Rican news portal";
				status obsolete;
			}

			enum "elnuevodiario" {
				opd:help "Nicaraguan news portal";
				status obsolete;
			}

			enum "elnuevoherald" {
				opd:help "Cuban news portal";
				status obsolete;
			}

			enum "elpais" {
				opd:help "Spanish news web portal, also accessed from Uruguay and Colombia";
				status obsolete;
			}

			enum "elsalvador" {
				opd:help "EL Salvadorian news portal";
				status obsolete;
			}

			enum "eltiempo" {
				opd:help "Colombian news portal";
				status obsolete;
			}

			enum "eluniverso" {
				opd:help "Ecuadorian news portal";
				status obsolete;
			}

			enum "elwatannews" {
				opd:help "Egyptian news portal";
				status obsolete;
			}

			enum "emag" {
				opd:help "Romanian classified ads website";
				status obsolete;
			}

			enum "emansion_lr" {
				opd:help "Official government site of Liberia";
				status obsolete;
			}

			enum "emaps" {
				opd:help "(Deprecated) This classifies the HTTP traffic to the host empas.com";
				status obsolete;
			}

			enum "emcon" {
				opd:help "The emcon protocol (EMCON) is found over the IP layer (IANA protocol number: 14)";
				status obsolete;
			}

			enum "emisoras_unidas" {
				opd:help "Online radio and news portal from Guatemala";
				status obsolete;
			}

			enum "emol" {
				opd:help "Chilean news portal";
				status obsolete;
			}

			enum "emoo" {
				opd:help "Local online community website from Bermuda, featuring classified ads, directory, guides, etc";
				status obsolete;
			}

			enum "empire_four_kingdoms" {
				opd:help "Mobile game";
				status obsolete;
			}

			enum "encap" {
				opd:help "The encap protocol (Encapsulation Header) is found over the IP layer (IANA protocol number: 98)";
				status obsolete;
			}

			enum "encuentra24" {
				opd:help "Official Panama Classifieds Portal";
				status obsolete;
			}

			enum "energy_torrent" {
				opd:help "BitTorrent tracker search engine";
				status obsolete;
			}

			enum "enip" {
				opd:help "ENIP (EtherNet/IP) is an industrial network protocol that adapts the Common Industrial Protocol to standard Ethernet";
				status obsolete;
			}

			enum "ensighten" {
				opd:help "Ensighten is a global omni-channel data and tag management technology vendor";
				status obsolete;
			}

			enum "ensonhaber" {
				opd:help "News portal popular in Turkey";
				status obsolete;
			}

			enum "eons" {
				opd:help "This classifies the HTTP traffic to the host eons.com";
				status obsolete;
			}

			enum "epa" {
				opd:help "Paraguayan celebrity news website";
				status obsolete;
			}

			enum "epernicus" {
				opd:help "This classifies the HTTP traffic to the host epernicus.com";
				status obsolete;
			}

			enum "epl" {
				opd:help "English Premier League (EPL) application is provided by Optus (Australian Mobile Operator)";
				status obsolete;
			}

			enum "epm" {
				opd:help "End Point Mapper is a protocol used by Exchange to determine the ports used by various services";
				status obsolete;
			}

			enum "epom" {
				opd:help "Epom is an ad platform for advertisers, publishers, ad networks, and ad agencies";
				status obsolete;
			}

			enum "eroom_net" {
				opd:help "This classifies the SSL traffic to the Common Name project1.eroom.net";
				status obsolete;
			}

			enum "eskimi" {
				opd:help "Eskimi is a social networking platform, and online chat, to meet people";
				status obsolete;
			}

			enum "esnips" {
				opd:help "This classifies the HTTP traffic to the host esnips.com";
				status obsolete;
			}

			enum "esp" {
				opd:help "(Deprecated) The ESP protocol (Encap Security Payload) is found over the IP layer (IANA protocol number: 50)";
				status obsolete;
			}

			enum "espn" {
				opd:help "American news website/resources about sports";
				status obsolete;
			}

			enum "espncricinfo" {
				opd:help "International cricket news, live scores, photos, columns and player profiles";
				status obsolete;
			}

			enum "essada" {
				opd:help "News web portal popular in Tunisia";
				status obsolete;
			}

			enum "essaha" {
				opd:help "Infotainment web portal popular in Mauritania";
				status obsolete;
			}

			enum "essahraa" {
				opd:help "Mauritanian news portal";
				status obsolete;
			}

			enum "essirage" {
				opd:help "Mauritanian news portal";
				status obsolete;
			}

			enum "established" {
				opd:help "The Established protocol is a virtual protocol grouping all TCP connections already established before starting analyzing the traffic (no SYNC)";
				status obsolete;
			}

			enum "estadio" {
				opd:help "Ecuadorian news portal specialized in sports";
				status obsolete;
			}

			enum "etajakhabar" {
				opd:help "Nepali news portal";
				status obsolete;
			}

			enum "etao" {
				opd:help "eTao is a comprehensive shopping search engine in China in terms of product and merchant information";
				status obsolete;
			}

			enum "etecsa" {
				opd:help "Government owned telco service provider for the Island of Cuba";
				status obsolete;
			}

			enum "ethiojobs" {
				opd:help "Ethiopian job ads";
				status obsolete;
			}

			enum "ethiotube" {
				opd:help "Ethiopian video hosting website";
				status obsolete;
			}

			enum "etsi_li" {
				opd:help "Etsi LI is a protocol which forms a standard for telecoms operators and networks operators";
				status obsolete;
			}

			enum "ettoday" {
				opd:help "ETtoday.net provide real-time news, including political, financial, social and international news, as well as life, consumption, pets, novelty, entertainment, sports, travel information and related news stories";
				status obsolete;
			}

			enum "eve_online" {
				opd:help "Eve Online is a multiplayer online game edited by CCP";
				status obsolete;
			}

			enum "everest_tech" {
				opd:help "Everest Technologies is an Information Technology solutions provider";
				status obsolete;
			}

			enum "evernote" {
				opd:help "Web-based portal for note taking";
				status obsolete;
			}

			enum "everquest" {
				opd:help "Everquest is a 3D fantasy massively multiplayer online role-playing game (MMORPG), for Windows platforms, developed by Sony Online Entertainment (SOE)";
				status obsolete;
			}

			enum "evony" {
				opd:help "This classifies the traffic to the host evony.com";
				status obsolete;
			}

			enum "exacqvision" {
				opd:help "Exacqvision is a software used for video surveillance";
				status obsolete;
			}

			enum "exblog" {
				opd:help "Japanese blog hosting services owned by Excite";
				status obsolete;
			}

			enum "excel_online" {
				opd:help "On-line version of Microsoft Excel";
				status obsolete;
			}

			enum "exelate" {
				opd:help "eXelate is a provider of data technology powering the digital marketing";
				status obsolete;
			}

			enum "expatriates" {
				opd:help "International Classified Ads website for expatriates";
				status obsolete;
			}

			enum "expedia" {
				opd:help "This classifies the HTTP traffic to the hosts expedia.com and expedia.fr";
				status obsolete;
			}

			enum "experience_project" {
				opd:help "This classifies the HTTP traffic to the host experienceproject.com";
				status obsolete;
			}

			enum "exploroo" {
				opd:help "This classifies the HTTP traffic to the host exploroo.com";
				status obsolete;
			}

			enum "expressen" {
				opd:help "Swedish news portal";
				status obsolete;
			}

			enum "extremebits" {
				opd:help "BitTorrent tracker search engine";
				status obsolete;
			}

			enum "extremenova" {
				opd:help "BitTorrent tracker search engine";
				status obsolete;
			}

			enum "eyejot" {
				opd:help "This classifies the HTTP traffic to the hosts eyejot.com, eyejot.typepad.com and eyejot.uservoice.com";
				status obsolete;
			}

			enum "eyny" {
				opd:help "Hot topic, leisure and entertainment, academic, computer, information exchange forum";
				status obsolete;
			}

			enum "ezfly" {
				opd:help "Taiwanese online travel agency";
				status obsolete;
			}

			enum "ezpeer" {
				opd:help "P2P service for music files downloading (aka ezPeer)";
				status obsolete;
			}

			enum "eztravel" {
				opd:help "Taiwanese online travel agency";
				status obsolete;
			}

			enum "facebook" {
				opd:help "Facebook is a social network";
				status obsolete;
			}

			enum "facebook_apps" {
				opd:help "Facebook Applications";
				status obsolete;
			}

			enum "facebook_live" {
				opd:help "Free live video streaming service by Facebook";
				status obsolete;
			}

			enum "facebook_mail" {
				opd:help "(Deprecated) Facebook Mail is a webmail environment in Facebook";
				status obsolete;
			}

			enum "facebook_messenger" {
				opd:help "Facebook Messenger is an instant messaging service available on desktop and mobile devices";
				status obsolete;
			}

			enum "facebook_video" {
				opd:help "Facebook Embedded Video is a Facebook service allowing to watch, upload and share videos";
				status obsolete;
			}

			enum "facenama" {
				opd:help "Iranian social network";
				status obsolete;
			}

			enum "faceparty" {
				opd:help "This classifies the HTTP traffic to the host faceparty.com";
				status obsolete;
			}

			enum "faces" {
				opd:help "This classifies the HTTP traffic to the host faces.com";
				status obsolete;
			}

			enum "facetime" {
				opd:help "FaceTime is an Apple video calling software which runs on iOS based mobile devices";
				status obsolete;
			}

			enum "fanpage" {
				opd:help "Greek website that deals with topics based around society and lifestyle";
				status obsolete;
			}

			enum "farmville" {
				opd:help "FarmVille is a farming simulation social network game developed by Zynga";
				status obsolete;
			}

			enum "farsnews" {
				opd:help "Iranian news portal";
				status obsolete;
			}

			enum "fashionguide" {
				opd:help "Fashion, beauty, discount information guide, fashion and beauty forum, cosmetic reviews";
				status obsolete;
			}

			enum "fastly" {
				opd:help "Fastly is a real-time CDN";
				status obsolete;
			}

			enum "fatakat" {
				opd:help "Egyptian portal targeted to Arab women's lifestyle";
				status obsolete;
			}

			enum "fatunetwork" {
				opd:help "Popular news and entertainment portal in Gambia";
				status obsolete;
			}

			enum "fbcdn" {
				opd:help "FBCDN is the Facebook Content Delivery Network (CDN) service, mostly used for static content access such as photos";
				status obsolete;
			}

			enum "fc2" {
				opd:help "Japanese free blog platform and social website";
				status obsolete;
			}

			enum "fcm" {
				opd:help "Firebase Cloud Messaging (FCM) is the new version of GCM";
				status obsolete;
			}

			enum "feiliao" {
				opd:help "feiliao is a Chinese instant messaging application";
				status obsolete;
			}

			enum "femina" {
				opd:help "Women news, trends and gears specialised websites";
				status obsolete;
			}

			enum "fenopy" {
				opd:help "BitTorrent tracker search engine";
				status obsolete;
			}

			enum "fetchtv" {
				opd:help "Personal Video recorder and Pay TV service delivered over broadband connection to the TV via a Fetch TV box";
				status obsolete;
			}

			enum "fetion" {
				opd:help "Fetion is a Chinese instant messaging application provided by China Mobile";
				status obsolete;
			}

			enum "fetlife" {
				opd:help "This classifies the HTTP traffic to the host fetlife.com";
				status obsolete;
			}

			enum "fibre_channel" {
				opd:help "The fibre_channel protocol (Fibre Channel) is found over the IP layer (IANA protocol number: 133)";
				status obsolete;
			}

			enum "fijitimes" {
				opd:help "Fijian news portal";
				status obsolete;
			}

			enum "fijivillage" {
				opd:help "Fiji web portal containing news, announcements, community information, business and shopping directory and radio stations";
				status obsolete;
			}

			enum "file_dropper" {
				opd:help "File hosting and sharing website";
				status obsolete;
			}

			enum "file_host" {
				opd:help "File hosting and sharing website from Romania";
				status obsolete;
			}

			enum "filefactory_com" {
				opd:help "Classifies web browsing on the filefactory.com Direct DownLoad links service";
				status obsolete;
			}

			enum "fileflyer" {
				opd:help "FileFlyer is an online solution to store, send and share files";
				status obsolete;
			}

			enum "fileguri" {
				opd:help "File sharing website and P2P client";
				status obsolete;
			}

			enum "filei" {
				opd:help "P2P website";
				status obsolete;
			}

			enum "filelist" {
				opd:help "Romanian torrent indexing website";
				status obsolete;
			}

			enum "filemail" {
				opd:help "File transfer service for private business";
				status obsolete;
			}

			enum "filemaker_pro" {
				opd:help "FileMaker Pro is a relational database application from FileMaker Inc. which runs on Microsoft Windows as well as Mac OS";
				status obsolete;
			}

			enum "filepost_ru" {
				opd:help "Classifies web browsing on the filepost.ru Direct DownLoad links service";
				status obsolete;
			}

			enum "filer_cx" {
				opd:help "(Deprecated) This classifies the HTTP traffic to the host filer.cx";
				status obsolete;
			}

			enum "filer_net" {
				opd:help "Classifies web browsing on the filer.net Direct DownLoad links service";
				status obsolete;
			}

			enum "filerio" {
				opd:help "FileRIO is a file sharing service";
				status obsolete;
			}

			enum "files_to" {
				opd:help "(Deprecated) This classifies the HTTP traffic to the host files.to";
				status obsolete;
			}

			enum "filesanywhere" {
				opd:help "File hosting and backup web service";
				status obsolete;
			}

			enum "filesend_net" {
				opd:help "(Deprecated) Classified web browsing on the filesend.net Direct DownLoad links service";
				status obsolete;
			}

			enum "fileserve" {
				opd:help "Fileserve is a file share service for personal use";
				status obsolete;
			}

			enum "filesharepro" {
				opd:help "File transfer application, allowing file sharing on a LAN network, or on the Internet";
				status obsolete;
			}

			enum "filesovermiles" {
				opd:help "Filesovermiles is a p2p written in Flash which is meant to be executed from a browser page (blocking use case is supported but flow classification is limited to web)";
				status obsolete;
			}

			enum "filestube" {
				opd:help "(Deprecated) This used to classify web access to the FilesTube metasearch engine";
				status obsolete;
			}

			enum "filetopia" {
				opd:help "Filetopia is a free, proprietary peer-to-peer client software for Windows";
				status obsolete;
			}

			enum "fillos_de_galicia" {
				opd:help "This classifies the HTTP traffic to the host fillos.org";
				status obsolete;
			}

			enum "filmaffinity" {
				opd:help "This classifies the traffic to the host filmaffinity.com";
				status obsolete;
			}

			enum "find_my_iphone" {
				opd:help "Application developed by Apple to find a lost iOS device";
				status obsolete;
			}

			enum "finn" {
				opd:help "Norwegian web portal";
				status obsolete;
			}

			enum "fire" {
				opd:help "The fire protocol (FIRE) is found over the IP layer (IANA protocol number: 125)";
				status obsolete;
			}

			enum "firefox_update" {
				opd:help "Mozilla Firefox update protocol for the browser and its plugins";
				status obsolete;
			}

			enum "fix" {
				opd:help "Electronic communications protocol for international real-time transactions and markets information exchange";
				status obsolete;
			}

			enum "flash" {
				opd:help "Adobe Flash Media Playback is a dynamic HTTP streaming protocol used to access video contents from a smart client application";
				status obsolete;
			}

			enum "flashplugin_update" {
				opd:help "Flash exchanges plug-in version numbers with Adobe servers";
				status obsolete;
			}

			enum "flashtalking" {
				opd:help "Flashtalking is an ad serving, tracking and technology company";
				status obsolete;
			}

			enum "fledgewing" {
				opd:help "(Deprecated) This classifies the HTTP traffic to the host fledgewing.com";
				status obsolete;
			}

			enum "flickr" {
				opd:help "Image hosting and sharing website with social and blogging services";
				status obsolete;
			}

			enum "flipagram" {
				opd:help "Flipagram is a tool to create, share and discover photos and videos";
				status obsolete;
			}

			enum "flipboard" {
				opd:help "Flipboard is a social-network aggregation web service for browsers and mobile devices";
				status obsolete;
			}

			enum "flipkart" {
				opd:help "Indian ecommerce website";
				status obsolete;
			}

			enum "flixster" {
				opd:help "This classifies the HTTP traffic to the host flixster.com";
				status obsolete;
			}

			enum "flumotion" {
				opd:help "This classifies the HTTP traffic to the host flumotion.com";
				status obsolete;
			}

			enum "flurry" {
				opd:help "Flurry provides services to optimize customer's mobile experience through apps and personalized ads";
				status obsolete;
			}

			enum "fluxiom" {
				opd:help "This classifies the HTTP traffic to the host fluxiom.com";
				status obsolete;
			}

			enum "fly_proxy" {
				opd:help "This classifies the HTTP traffic to the host flyproxy.com";
				status obsolete;
			}

			enum "flycell_ec" {
				opd:help "SMS alerts service based in Ecuador";
				status obsolete;
			}

			enum "flycell_pe" {
				opd:help "Peruvian ringtone, wallpaper and mobile game portal";
				status obsolete;
			}

			enum "fnb" {
				opd:help "South African banking website";
				status obsolete;
			}

			enum "fnu" {
				opd:help "Website of the Fiji National University";
				status obsolete;
			}

			enum "fogbugz" {
				opd:help "This classifies the HTTP traffic to the host fogbugz.com";
				status obsolete;
			}

			enum "foreningssparbanken" {
				opd:help "(Deprecated) Swedish web portal";
				status obsolete;
			}

			enum "fortunechina" {
				opd:help "Chinese top fortune news portal";
				status obsolete;
			}

			enum "forum" {
				opd:help "Georgian general-purpose forum launched in 2001, also known as Tbilisis Forumi";
				status obsolete;
			}

			enum "fotki" {
				opd:help "This classifies the HTTP and SSL traffic to the host fotki.com";
				status obsolete;
			}

			enum "fotolog" {
				opd:help "This classifies the HTTP traffic to the host fotolog.com";
				status obsolete;
			}

			enum "fotoweb" {
				opd:help "Digital asset management workflow solutions";
				status obsolete;
			}

			enum "foursquare" {
				opd:help "Foursquare is a local search-and-discovery service mobile app which provides search results for its users";
				status obsolete;
			}

			enum "foxbusiness" {
				opd:help "Fox Business Network (FBN) is an American cable and satellite business news television channel that is owned by the Fox Entertainment Group division of 21st Century Fox";
				status obsolete;
			}

			enum "foxmovies" {
				opd:help "This classifies the HTTP traffic to the hosts foxmovies.jp, foxmovies.com";
				status obsolete;
			}

			enum "foxnews" {
				opd:help "Fox News is an American news television channel, which allows news reports browsing and video watching on its website";
				status obsolete;
			}

			enum "foxsports" {
				opd:help "Foxsports.com is an American sports live video streaming website";
				status obsolete;
			}

			enum "foxsports_au" {
				opd:help "Australian sports live video streaming of Footy, Rugby, Soccer, Cricket, Motorsport, Tennis and much more";
				status obsolete;
			}

			enum "foxtel" {
				opd:help "Foxtel is a Video streaming website, proposing live stream or VOD";
				status obsolete;
			}

			enum "foxy" {
				opd:help "Foxy is a peer-to-peer protocol based on GnucDNA";
				status obsolete;
			}

			enum "free" {
				opd:help "French ISP and mobile operator website";
				status obsolete;
			}

			enum "free_music_download" {
				opd:help "Download, play, sort, organize media files";
				status obsolete;
			}

			enum "freebsd_update" {
				opd:help "This protocol is used for FreeBSD updates";
				status obsolete;
			}

			enum "freedomnewspaper" {
				opd:help "Online newspaper portal popular in Gambia";
				status obsolete;
			}

			enum "freeetv" {
				opd:help "This classifies the HTTP traffic to the host freeetv.com";
				status obsolete;
			}

			enum "freeloader" {
				opd:help "BitTorrent tracker search engine";
				status obsolete;
			}

			enum "freemail" {
				opd:help "Hungarian webmail";
				status obsolete;
			}

			enum "freenet" {
				opd:help "Freenet is an application that intends to provide online anonymity";
				status obsolete;
			}

			enum "freeproxies" {
				opd:help "Proxy hosting service (redirector and anonymizer) that uses the CGI Proxy script";
				status obsolete;
			}

			enum "freetorrent" {
				opd:help "BitTorrent tracker search engine";
				status obsolete;
			}

			enum "freewheel" {
				opd:help "FreeWheel provides ad management and monetization, a private marketplace for premium television inventory, and advisory services for video streaming industry";
				status obsolete;
			}

			enum "freshnewsasia" {
				opd:help "Cambodian news feed website";
				status obsolete;
			}

			enum "friends_reunited" {
				opd:help "This classifies the HTTP traffic to the host friendsreunited.com";
				status obsolete;
			}

			enum "friendster" {
				opd:help "(Deprecated) Friendster was a social networking website, enabling users to connect to relatives, friends, or unknown people";
				status obsolete;
			}

			enum "friendvox" {
				opd:help "This classifies the HTTP traffic to the host friendvox.com";
				status obsolete;
			}

			enum "fring" {
				opd:help "Fring is a peer-to-peer Mobile VoIP based Internet telephony network";
				status obsolete;
			}

			enum "frostwire" {
				opd:help "FrostWire is a BitTorrent client";
				status obsolete;
			}

			enum "fruhstuckstreff" {
				opd:help "This classifies the HTTP and SSL traffic to the host fruehstueckstreff.de";
				status obsolete;
			}

			enum "fruit_ninja" {
				opd:help "Mobile game";
				status obsolete;
			}

			enum "fsecure" {
				opd:help "F-Secure Corporation is a Finnish computer security company";
				status obsolete;
			}

			enum "fsecure_update" {
				opd:help "Fsecure_update is the protocol used for Fsecure software updates";
				status obsolete;
			}

			enum "ftp" {
				opd:help "The FTP protocol is used for reliable data transfer between a client and a server";
				status obsolete;
			}

			enum "ftp_data" {
				opd:help "This protocol is used to transport data in data connection of FTP communication";
				status obsolete;
			}

			enum "ftps" {
				opd:help "Secure version of the FTP protocol";
				status obsolete;
			}

			enum "fubar" {
				opd:help "This classifies the HTTP and SSL traffic to the host fubar.com";
				status obsolete;
			}

			enum "funcaptcha" {
				opd:help "Funcaptcha is a software to stop spam, verify humans and earn revenue";
				status obsolete;
			}

			enum "funshion" {
				opd:help "Funshion player is a Chinese service for downloading and streaming movies";
				status obsolete;
			}

			enum "fuze_meeting" {
				opd:help "Video-conferencing application (audio, video HD, desktop sharing, file transfer)";
				status obsolete;
			}

			enum "gabonreview" {
				opd:help "Daily news website in Gabon";
				status obsolete;
			}

			enum "gadugadu" {
				opd:help "Gadu Gadu is a Polish instant messaging protocol";
				status obsolete;
			}

			enum "gaiaonline" {
				opd:help "This classifies the HTTP traffic to the host gaiaonline.com";
				status obsolete;
			}

			enum "game_center" {
				opd:help "Online multiplayer social gaming network by Apple";
				status obsolete;
			}

			enum "gamebase_tw" {
				opd:help "Taiwanese game information portal providing game reviews, walkthrough, cheats";
				status obsolete;
			}

			enum "gameloft" {
				opd:help "Games for mobile devices by Gameloft";
				status obsolete;
			}

			enum "gamer_tw" {
				opd:help "Taiwanese game portal providing game reviews, forum, news";
				status obsolete;
			}

			enum "gamerdna" {
				opd:help "(Deprecated) This classifies the HTTP traffic to the host gamerdna.com";
				status obsolete;
			}

			enum "games_co" {
				opd:help "This classifies the HTTP traffic to the host games.co.id";
				status obsolete;
			}

			enum "gamesmomo" {
				opd:help "Selection of fun games, Flash Games";
				status obsolete;
			}

			enum "ganji" {
				opd:help "This classifies the HTTP traffic to the host ganji.com";
				status obsolete;
			}

			enum "garaanews" {
				opd:help "Jordanian news portal";
				status obsolete;
			}

			enum "garena" {
				opd:help "Garena is a platform provider for online entertainment and communication tools";
				status obsolete;
			}

			enum "gather" {
				opd:help "This classifies the HTTP traffic to the host gather.com";
				status obsolete;
			}

			enum "gatherplace" {
				opd:help "Gatherplace is a web conferencing software";
				status obsolete;
			}

			enum "gays" {
				opd:help "This classifies the HTTP traffic to the host gays.com";
				status obsolete;
			}

			enum "gazeta" {
				opd:help "Polish news portal";
				status obsolete;
			}

			enum "gazetablic" {
				opd:help "Web portal featuring breaking news, analysis, commentary from Kosovo, Region and the World";
				status obsolete;
			}

			enum "gazetaexpress" {
				opd:help "Albanian news portal";
				status obsolete;
			}

			enum "gazzetta" {
				opd:help "Greek news portal";
				status obsolete;
			}

			enum "gbridge" {
				opd:help "Gbridge is a free software that lets you remotely control PCs, sync folders, share files, and chat securely";
				status obsolete;
			}

			enum "gcm" {
				opd:help "Data exchange service between 3rd party server applications and Android client applications";
				status obsolete;
			}

			enum "gcs" {
				opd:help "Online file storage web service for applications by Google";
				status obsolete;
			}

			enum "gdb_remote" {
				opd:help "GDB Remote is a serial protocol used connect gdb to a remote running target program and debug it";
				status obsolete;
			}

			enum "geni" {
				opd:help "This classifies the HTTP traffic to the host geni.com";
				status obsolete;
			}

			enum "gerasanews" {
				opd:help "Jordanian news portal";
				status obsolete;
			}

			enum "gettyimages" {
				opd:help "Getty Images distributes still imagery, video, music and multimedia products, as well as other forms of premium digital content";
				status obsolete;
			}

			enum "gfan" {
				opd:help "A large Android community providing ROM, applications, tutorials and other content";
				status obsolete;
			}

			enum "gfycat" {
				opd:help "Gfycat is a web platform for uploading and hosting short video content";
				status obsolete;
			}

			enum "ggp" {
				opd:help "The ggp protocol (Gateway_to_Gateway) is found over the IP layer (IANA protocol number: 3)";
				status obsolete;
			}

			enum "ghanaweb" {
				opd:help "Ghanaian news portal";
				status obsolete;
			}

			enum "ghostsurf" {
				opd:help "GhostSurf is an internet privacy application";
				status obsolete;
			}

			enum "gigacircle" {
				opd:help "Taiwanese blogging platform";
				status obsolete;
			}

			enum "gigasize_com" {
				opd:help "Classifies web browsing on the gigasize.com Direct DownLoad links service";
				status obsolete;
			}

			enum "gigatribe" {
				opd:help "GigaTribe is a peer-to-peer file sharing network (classification of web/authentication part only)";
				status obsolete;
			}

			enum "gigaup" {
				opd:help "(Deprecated) This used to classify the gigaup.fr DDL service";
				status obsolete;
			}

			enum "giop" {
				opd:help "The General Inter-Orb protocol (GIOP) is used to make requests or return replies between ORBs in a Corba environment";
				status obsolete;
			}

			enum "giops" {
				opd:help "This protocol is the secure version of the GIOP protocol";
				status obsolete;
			}

			enum "giphy" {
				opd:help "Giphy is a service which allows sharing and discovering animated GIFs in several mobile applications, like Tinder, Whatsapp, etc";
				status obsolete;
			}

			enum "github" {
				opd:help "Famous web-based code repository for open source software development";
				status obsolete;
			}

			enum "gizmo" {
				opd:help "(Deprecated) Gizmo was an instant messaging service, acquired and closed by Google";
				status obsolete;
			}

			enum "glide" {
				opd:help "This classifies the HTTP traffic to the host desktop.glidesociety.com";
				status obsolete;
			}

			enum "globalpublishers" {
				opd:help "Tanzanian news portal";
				status obsolete;
			}

			enum "globo" {
				opd:help "Brazilian news portal";
				status obsolete;
			}

			enum "glympse" {
				opd:help "Glympse is a fast, free, and simple way to share your location in real-time";
				status obsolete;
			}

			enum "gmail" {
				opd:help "Gmail is the Google webmail service";
				status obsolete;
			}

			enum "gmail_basic" {
				opd:help "Gmail basic is the HTML version of the Google Webmail service";
				status obsolete;
			}

			enum "gmail_chat" {
				opd:help "Google chat is an online Webmessenger from Google";
				status obsolete;
			}

			enum "gmail_drive" {
				opd:help "GMAIL Drive is a Shell Namespace Extension that creates a virtual file system around a Google Mail account, allowing Gmail as a storage medium";
				status obsolete;
			}

			enum "gmail_mobile" {
				opd:help "Gmail_mobile is the Google webmail for mobile phones";
				status obsolete;
			}

			enum "gmanetwork" {
				opd:help "Filipino website about news and entertainment";
				status obsolete;
			}

			enum "gmarket" {
				opd:help "This classifies the HTTP and SSL traffic to the host gmarket.co.kr";
				status obsolete;
			}

			enum "gmtp" {
				opd:help "The gmtp protocol (GMTP) is found over the IP layer (IANA protocol number: 100)";
				status obsolete;
			}

			enum "gmw" {
				opd:help "Chinese news portal";
				status obsolete;
			}

			enum "gmx" {
				opd:help "GMX is a German webmail";
				status obsolete;
			}

			enum "gnunet" {
				opd:help "GNUnet is a framework for secure peer-to-peer networking mainly used for anonymous file sharing";
				status obsolete;
			}

			enum "gnutella" {
				opd:help "Gnutella is a peer-to-peer protocol";
				status obsolete;
			}

			enum "go90" {
				opd:help "Internet TV service owned by Verizon";
				status obsolete;
			}

			enum "goal" {
				opd:help "New media company that provides soccer news and entertainment";
				status obsolete;
			}

			enum "gob" {
				opd:help "Bolivian government portal";
				status obsolete;
			}

			enum "goboogy" {
				opd:help "GoBoogy is a peer-to-peer (p2p) application used to share files with other GoBoogy users over the Internet";
				status obsolete;
			}

			enum "godtube" {
				opd:help "GodTube is an online video sharing platform which strives to have Christian content";
				status obsolete;
			}

			enum "gogo" {
				opd:help "Mongolian search engine and web portal";
				status obsolete;
			}

			enum "gogobox" {
				opd:help "Cloud file storage web service";
				status obsolete;
			}

			enum "gogoyoko" {
				opd:help "(Deprecated) This classified the HTTP traffic to the host gogoyoko.com";
				status obsolete;
			}

			enum "gohappy" {
				opd:help "Taiwanese E-commerce web portal";
				status obsolete;
			}

			enum "golden_village" {
				opd:help "Singaporian online cinema ticket booking";
				status obsolete;
			}

			enum "goldenfrog" {
				opd:help "Golden Frog develops software and online services focused on privacy and security";
				status obsolete;
			}

			enum "gomeetnow" {
				opd:help "Gomeetnow is a web conferencing software";
				status obsolete;
			}

			enum "gomtv_vod" {
				opd:help "Gom TV is a social video website designed for gamers";
				status obsolete;
			}

			enum "goo_ne" {
				opd:help "Japanese web portal owned by NTT";
				status obsolete;
			}

			enum "goodreads" {
				opd:help "This classifies the HTTP traffic to the host goodreads.com";
				status obsolete;
			}

			enum "google" {
				opd:help "This protocol is used for sending user queries to the Google search engine";
				status obsolete;
			}

			enum "google_accounts" {
				opd:help "Detects SSL access to the Google Accounts server";
				status obsolete;
			}

			enum "google_ads" {
				opd:help "Google Ads is the online advertisement service from Google";
				status obsolete;
			}

			enum "google_analytics" {
				opd:help "Google Analytics is the enterprise-class web analytics solution that gives you rich insights into your website traffic and marketing effectiveness";
				status obsolete;
			}

			enum "google_appengine" {
				opd:help "Google App Engine is a platform as a service (PaaS) cloud computing platform for developing and hosting web applications in Google-managed data centers";
				status obsolete;
			}

			enum "google_cache" {
				opd:help "Google Cache saves a copy of the webpages which were found by the Google search engine";
				status obsolete;
			}

			enum "google_calendar" {
				opd:help "Google Calendar is a Google free online calendar";
				status obsolete;
			}

			enum "google_classroom" {
				opd:help "Learning management system for schools by Google";
				status obsolete;
			}

			enum "google_code" {
				opd:help "Google Code is a website for developers interested in developing on Google";
				status obsolete;
			}

			enum "google_desktop" {
				opd:help "(Deprecated) Google Desktop is a desktop search software made by Google, with indexed document metadata";
				status obsolete;
			}

			enum "google_docs" {
				opd:help "On-line file storage and sharing web-service by Google";
				status obsolete;
			}

			enum "google_earth" {
				opd:help "Google Earth is a program used to view a virtual Earth in 3D";
				status obsolete;
			}

			enum "google_gen" {
				opd:help "This protocol is a generic layer used as a base for all the Google protocols";
				status obsolete;
			}

			enum "google_groups" {
				opd:help "Google Groups allows the user to create and post in forums and email-based groups";
				status obsolete;
			}

			enum "google_inbox" {
				opd:help "Inbox by Gmail is an email app by Google";
				status obsolete;
			}

			enum "google_localguides" {
				opd:help "Local Guides is a global community of explorers sharing their discoveries on Google Maps";
				status obsolete;
			}

			enum "google_maps" {
				opd:help "Google Maps can be used to calculate routes and to look at maps";
				status obsolete;
			}

			enum "google_photos" {
				opd:help "Google Photos is a digital photo and video organizer used to edit and synchronize pictures or videos over the web";
				status obsolete;
			}

			enum "google_picasa" {
				opd:help "(Deprecated) Google Picasa is a digital photo and video organizer used to edit and synchronize pictures or videos over the web";
				status obsolete;
			}

			enum "google_play" {
				opd:help "Google Play Store (formerly Android Market) is an online software store developed by Google for Android OS devices";
				status obsolete;
			}

			enum "google_play_music" {
				opd:help "Google Play Music is a music streaming service and online music locker operated by Google";
				status obsolete;
			}

			enum "google_plus" {
				opd:help "Google Plus is a social network";
				status obsolete;
			}

			enum "google_safebrowsing" {
				opd:help "Google Safe Browsing is a web-service and API for checking web pages against threats";
				status obsolete;
			}

			enum "google_skymap" {
				opd:help "Google Sky Map is an outer space viewer Android mobile application";
				status obsolete;
			}

			enum "google_spaces" {
				opd:help "A cross-platform application for group messaging and sharing";
				status obsolete;
			}

			enum "google_sprayscape" {
				opd:help "Sprayscape is a photo application for mobile devices running Android, developed by Google";
				status obsolete;
			}

			enum "google_supl" {
				opd:help "Google SUPL is the Secure User Plane Location (SUPL) generated by Android";
				status obsolete;
			}

			enum "google_tags" {
				opd:help "Google Tag Manager is a tag manager for website and mobile applications";
				status obsolete;
			}

			enum "google_toolbar" {
				opd:help "The Google Toolbar is an extension for Internet Explorer and Mozilla Firefox which provides a search box, a pop-up blocker, a translator, etc";
				status obsolete;
			}

			enum "google_translate" {
				opd:help "Google Translate is the Google translation tool";
				status obsolete;
			}

			enum "google_trusted_store" {
				opd:help "Google Trusted Store classifies access to the Google Trusted Store web API";
				status obsolete;
			}

			enum "google_weblight" {
				opd:help "Allows to get a faster loading of web pages by browsing a lightweight version of websites";
				status obsolete;
			}

			enum "googlebot" {
				opd:help "Web crawler (spider) used by the Google Search engine";
				status obsolete;
			}

			enum "goose" {
				status obsolete;
			}

			enum "goplan" {
				opd:help "Goplan is an online project management and collaboration tool for individuals and teams";
				status obsolete;
			}

			enum "gossiplankanews" {
				opd:help "SriLankan news portal";
				status obsolete;
			}

			enum "gotodevice" {
				opd:help "GoToDevice is a remote control and administration tool";
				status obsolete;
			}

			enum "gotomeeting" {
				opd:help "GoToMeeting is an online meeting service developed by Citrix";
				status obsolete;
			}

			enum "gotomypc" {
				opd:help "Citrix GoToMyPC is a secured web-based remote access solution, enabling to take control of a PC/MAC from a web browser";
				status obsolete;
			}

			enum "gougou" {
				opd:help "Gougou is a Chinese web search engine";
				status obsolete;
			}

			enum "gozambiajobs" {
				opd:help "Job seeking website in Zambia";
				status obsolete;
			}

			enum "granma" {
				opd:help "The official website for the PCC (Partido Comunista de Cuba)";
				status obsolete;
			}

			enum "gratisindo" {
				opd:help "This classifies the gratisindo HTTP traffic";
				status obsolete;
			}

			enum "gravatar" {
				opd:help "Gravatar allows picture-based user identification";
				status obsolete;
			}

			enum "gree" {
				opd:help "Japanese web portal dedicated to smartphone games";
				status obsolete;
			}

			enum "greenarea" {
				opd:help "Lebanon news website publishing Environmental, Political, Social, Science, Technology and varieties news";
				status obsolete;
			}

			enum "grid" {
				opd:help "Macedonian news portal";
				status obsolete;
			}

			enum "grono" {
				opd:help "This classifies the HTTP traffic to the host grono.net";
				status obsolete;
			}

			enum "groove" {
				opd:help "Microsoft Office Groove is a desktop application designed for document collaboration in teams with members who are regularly off-line or who do not share the same network security clearance";
				status obsolete;
			}

			enum "grooveshark" {
				opd:help "(Deprecated) Grooveshark was an online unlimited service for music (closed on 2015-04-30)";
				status obsolete;
			}

			enum "groupon" {
				opd:help "This classifies the HTTP traffic to the hosts groupon.com, groupon.com.br, groupon.fr and groupon.jp";
				status obsolete;
			}

			enum "groupwise" {
				opd:help "Novell Groupwise is a groupware, instant-messaging and mail-application";
				status obsolete;
			}

			enum "gsshop" {
				opd:help "This classifies the HTTP and SSL traffic to the host gsshop.com";
				status obsolete;
			}

			enum "gstatic" {
				opd:help "GStatic is a download server providing static resources (like CSS) or scripts for Google web applications";
				status obsolete;
			}

			enum "gt_racing_2" {
				opd:help "Mobile game, edited by Gameloft";
				status obsolete;
			}

			enum "gtalk" {
				opd:help "This signature classifies part of the flows related to the Google IM and audio/video calls applications both for PC and mobile devices";
				status obsolete;
			}

			enum "gtpv2" {
				opd:help "The GPRS Tunneling Protocol (GTP) version 2 is used in G4 mobile networks (LTE)";
				status obsolete;
			}

			enum "guampdn" {
				opd:help "Guamanian news portal";
				status obsolete;
			}

			enum "guatevision" {
				opd:help "Guatemalan television channel website";
				status obsolete;
			}

			enum "gudanglagu" {
				opd:help "This classifies the HTTP traffic to the host gudanglagu.com";
				status obsolete;
			}

			enum "guineenews" {
				opd:help "News and classified ads website popular in Guinea";
				status obsolete;
			}

			enum "gulfup" {
				opd:help "Online file sharing website popular in Saudi Arabia and countries around the Gulf";
				status obsolete;
			}

			enum "gumtree" {
				opd:help "Gumtree is the first site for free classified ads in the UK for buying and selling items, cars, properties, and find or offer jobs";
				status obsolete;
			}

			enum "gyao" {
				opd:help "GyaO is a video website operated by Yahoo Japan";
				status obsolete;
			}

			enum "h225" {
				opd:help "The H225 Protocol is a VoIP protocol, used for call signaling and RAS (Registration, Admission and Status)";
				status obsolete;
			}

			enum "h245" {
				opd:help "H245 is a VoIP protocol, used for call signaling codec negotiation";
				status obsolete;
			}

			enum "h248_binary" {
				opd:help "h248 Protocol (Megaco) in binary mode";
				status obsolete;
			}

			enum "h248_text" {
				opd:help "h248 Protocol (Megaco) in text mode";
				status obsolete;
			}

			enum "habbo" {
				opd:help "Habbo is a is a social-networking site that offers games and chat";
				status obsolete;
			}

			enum "haber7" {
				opd:help "Turkish TV streaming website";
				status obsolete;
			}

			enum "halflife" {
				opd:help "Half-Life and Half-Life 2 are two first-person shooter video games developed by Valve Corporation and provide on-line gaming features";
				status obsolete;
			}

			enum "hamachi" {
				opd:help "Hamachi is a VPN service provided by LogMeIn";
				status obsolete;
			}

			enum "hamariweb" {
				opd:help "Infotainment web portal in Pakistan";
				status obsolete;
			}

			enum "hambastagi" {
				opd:help "Web portal of the Solidarity Party of Afghanistan (small political party)";
				status obsolete;
			}

			enum "handycafe" {
				opd:help "Cyber Internet Cafe management software including monitoring, membership accounting, firewall, etc";
				status obsolete;
			}

			enum "hangame" {
				opd:help "This classifies the HTTP and SSL traffic to the host hangame.com/.co.jp";
				status obsolete;
			}

			enum "hankooki" {
				opd:help "This classifies the HTTP traffic to the host hankooki.com";
				status obsolete;
			}

			enum "hankyung" {
				opd:help "This classifies the HTTP traffic to the host hankyung.com";
				status obsolete;
			}

			enum "hao123" {
				opd:help "This classifies the HTTP traffic to the host hao123.com";
				status obsolete;
			}

			enum "haqqin" {
				opd:help "Armenian news website";
				status obsolete;
			}

			enum "hardsextube" {
				opd:help "This classifies the HTTP traffic to the host hardsextube.com";
				status obsolete;
			}

			enum "hardwarezone" {
				opd:help "Singaporean website about hitec gears";
				status obsolete;
			}

			enum "hatena_ne" {
				opd:help "Japanese web portal dedicated to social networking";
				status obsolete;
			}

			enum "haveeru" {
				opd:help "Maldivian news portal";
				status obsolete;
			}

			enum "hbo_go" {
				opd:help "On-demand video streaming website powered by the HBO American TV channel";
				status obsolete;
			}

			enum "hbonordic" {
				opd:help "On-demand video streaming website powered by the HBO American TV channel but only available in Sweden, Norway, Denmark and Finland";
				status obsolete;
			}

			enum "heap" {
				opd:help "Heap is web and mobile analytics software library that automatically captures every user action in a Web or iOS app";
				status obsolete;
			}

			enum "heavy" {
				opd:help "News website";
				status obsolete;
			}

			enum "helpshift" {
				opd:help "Helpshift is a support desk platform for native apps";
				status obsolete;
			}

			enum "heraldm" {
				opd:help "This classifies the HTTP traffic to the host heraldm.com";
				status obsolete;
			}

			enum "here" {
				opd:help "On-line maps and localization service brought by NAVTEQ and Nokia Maps";
				status obsolete;
			}

			enum "heroku" {
				opd:help "Heroku is a cloud Platform-as-a-Service";
				status obsolete;
			}

			enum "hespress" {
				opd:help "Moroccan news portal";
				status obsolete;
			}

			enum "heureka" {
				opd:help "Czech e-commerce website";
				status obsolete;
			}

			enum "hexun" {
				opd:help "Chinese finance news portal";
				status obsolete;
			}

			enum "hgtv" {
				opd:help "This classifies the HTTP traffic to the host hgtv.com";
				status obsolete;
			}

			enum "hi5" {
				opd:help "Hi5 is a social networking website, enabling users to connect to relatives, friends, or unknown people";
				status obsolete;
			}

			enum "hibapress" {
				opd:help "Moroccan news portal";
				status obsolete;
			}

			enum "hidemyass" {
				opd:help "HideMyAss is an anonymizing web proxy";
				status obsolete;
			}

			enum "high_entropy" {
				opd:help "High Entropy is a virtual protocol used to detect potentially encrypted payloads";
				status obsolete;
			}

			enum "highwinds" {
				opd:help "Highwinds is a content delivery network";
				status obsolete;
			}

			enum "hihi2" {
				opd:help "Website specialised in international soccer";
				status obsolete;
			}

			enum "hinet_games" {
				opd:help "Taiwanese game portal providing game reviews, forum, news";
				status obsolete;
			}

			enum "hip" {
				opd:help "The hip protocol (Host Identity Protocol) is found over the IP layer (IANA protocol number: 139)";
				status obsolete;
			}

			enum "hir24" {
				opd:help "Hungarian news portal";
				status obsolete;
			}

			enum "hirufm" {
				opd:help "SriLankan radio website";
				status obsolete;
			}

			enum "hirunews" {
				opd:help "News Portal in SriLanka, broadcasting in Sinhalese, Tamil and English";
				status obsolete;
			}

			enum "hitbox" {
				opd:help "(Deprecated) Hitbox is a gaming and eSports live streaming platform";
				status obsolete;
			}

			enum "hk_observatory" {
				opd:help "HK Observatory is a weather forecast service in Hong Kong";
				status obsolete;
			}

			enum "hkgolden" {
				opd:help "Game and electronics news portal based in Hong Kong";
				status obsolete;
			}

			enum "hln" {
				opd:help "Belgian news portal";
				status obsolete;
			}

			enum "hmp" {
				opd:help "The hmp protocol (Host Monitoring) is found over the IP layer (IANA protocol number: 20)";
				status obsolete;
			}

			enum "hockeyapp" {
				opd:help "HockeyApp is a development interface for applications on desktop and mobile platforms";
				status obsolete;
			}

			enum "hockeycurve" {
				opd:help "Hockey Curve is a marketing technology service provider";
				status obsolete;
			}

			enum "hola" {
				opd:help "News and lifestyle webportal popular in Andorra";
				status obsolete;
			}

			enum "hola_webproxy" {
				opd:help "Free web proxy enabling users to browse the web without censorship or bandwidth throttling";
				status obsolete;
			}

			enum "honeywell_phd" {
				opd:help "Traffic related to Honeywell Process History Database (PHD)";
				status obsolete;
			}

			enum "hootsuite" {
				opd:help "Hootsuite is a social media management system";
				status obsolete;
			}

			enum "hopopt" {
				opd:help "The hopopt protocol (IPv6 Hop-by-Hop Option) is found over the IP layer (IANA protocol number: 0)";
				status obsolete;
			}

			enum "hospitality_club" {
				opd:help "This classifies the traffic to the host hospitalityclub.org";
				status obsolete;
			}

			enum "host" {
				opd:help "The host protocol (Any host internal protocol) is found over the IP layer (IANA protocol number: 61)";
				status obsolete;
			}

			enum "hotfile" {
				opd:help "On-line file sharing service";
				status obsolete;
			}

			enum "hotjar" {
				opd:help "Hotjar is a web and mobile website analytics services, providing heatmap, survey, feedback, etc";
				status obsolete;
			}

			enum "hotline" {
				opd:help "The Hotline protocol is used to upload/download files, to chat and to get news about chatters (it is not a peer-to-peer protocol)";
				status obsolete;
			}

			enum "hotspot_shield" {
				opd:help "The Hotspot Shield application secures internet connections made from public access points using a VPN network";
				status obsolete;
			}

			enum "hovrs" {
				opd:help "This classifies the HTTP traffic to the hosts i711.com, hovrs.com and purple.us";
				status obsolete;
			}

			enum "howcast" {
				opd:help "This classifies the HTTP and SSL traffic to the host howcast.com";
				status obsolete;
			}

			enum "howstuffworks" {
				opd:help "This classifies the HTTP traffic to the host howstuffworks.com";
				status obsolete;
			}

			enum "hpellc" {
				opd:help "HP Extended Local-Link Control is an LLC protocol enhancement";
				status obsolete;
			}

			enum "hs" {
				opd:help "Finnish news portal";
				status obsolete;
			}

			enum "hsbc" {
				opd:help "HSBC banking website";
				status obsolete;
			}

			enum "hsrp" {
				opd:help "The Cisco Hot Standby Router Protocol (HSRP) enables you to manage router redundancy in a network";
				status obsolete;
			}

			enum "http" {
				opd:help "The Hypertext Transfer Protocol (HTTP) is used for browsing the web";
				status obsolete;
			}

			enum "http2" {
				opd:help "HTTP/2 is the second major version of the HTTP network protocol used by the World Wide Web";
				status obsolete;
			}

			enum "http_proxy" {
				opd:help "Indicates that a flow is proxied through HTTP CONNECT mechanism";
				status obsolete;
			}

			enum "http_tunnel" {
				opd:help "HTTP Tunnel protocol is used to tunnel protocols inside an HTTP stream";
				status obsolete;
			}

			enum "https" {
				opd:help "HTTPS is the secure version of HTTP";
				status obsolete;
			}

			enum "huawei" {
				opd:help "Huawei is a Chinese multinational networking and telecommunications equipment and services company";
				status obsolete;
			}

			enum "huawei_update" {
				opd:help "Huawei Update classifies Huawei mobile device updates";
				status obsolete;
			}

			enum "hudong" {
				opd:help "(Deprecated) This classifies the HTTP traffic to the host hudong.com";
				status obsolete;
			}

			enum "huffington_post" {
				opd:help "The Huffington Post is an American online news aggregator and blog";
				status obsolete;
			}

			enum "hulu" {
				opd:help "Hulu is a free Video-On-Demand and video sharing service";
				status obsolete;
			}

			enum "hungrygowhere" {
				opd:help "Singaporean fooding website";
				status obsolete;
			}

			enum "hurriyet" {
				opd:help "Turkish news portal";
				status obsolete;
			}

			enum "hvg_hu" {
				opd:help "Football related Egyptian news portal";
				status obsolete;
			}

			enum "hyves" {
				opd:help "This classifies the HTTP traffic to the host hyves.nl";
				status obsolete;
			}

			enum "i2p" {
				opd:help "I2P (Invisible Internet Project) is an anonymous overlay network - a network within a network";
				status obsolete;
			}

			enum "i_gamer" {
				opd:help "Online games and manga website";
				status obsolete;
			}

			enum "i_nlsp" {
				opd:help "The i_nlsp protocol (Integrated Net Layer Security TUBA) is found over the IP layer (IANA protocol number: 52)";
				status obsolete;
			}

			enum "i_part" {
				opd:help "Taiwanese online dating site";
				status obsolete;
			}

			enum "iapp" {
				opd:help "News site about mobile applications";
				status obsolete;
			}

			enum "iatp" {
				opd:help "The iatp protocol (Interactive Agent Transfer Protocol) is found over the IP layer (IANA protocol number: 117)";
				status obsolete;
			}

			enum "iax" {
				opd:help "Inter Asterisk eXchange (IAX2) is a data exchange protocol between Asterisk servers";
				status obsolete;
			}

			enum "ibackup" {
				opd:help "ibackup is an online file backup protocol";
				status obsolete;
			}

			enum "ibay" {
				opd:help "Maldivian online classified ads";
				status obsolete;
			}

			enum "ibibo" {
				opd:help "This classifies the HTTP traffic to the host ibibo.com";
				status obsolete;
			}

			enum "ibm_tealeaf" {
				opd:help "Tealeaf, a provider of digital customer experience management and customer behavior analysis solutions, is now part of Customer Analytics at IBM";
				status obsolete;
			}

			enum "ica" {
				opd:help "ICA (Independent Computing Architecture) is a communication protocol and a property of the Citrix Company";
				status obsolete;
			}

			enum "icall" {
				opd:help "icall is proprietary voice/video over IP protocol";
				status obsolete;
			}

			enum "icap" {
				opd:help "The Internet Content Adaptation Protocol (ICAP) is a lightweight HTTP-like protocol which is used to extend transparent proxy servers, thereby freeing up resources and standardizing the way in which new features are implemented";
				status obsolete;
			}

			enum "iccp" {
				opd:help "IEC 60870-6/TASE.2 Inter-Control Center Communications Protocol (ICCP) provides data exchange over Wide Area Networks (WANs) between utility control centers, utilities, power pools, regional control centers, and Non-Utility Generators";
				status obsolete;
			}

			enum "icecast" {
				opd:help "Icecast is a protocol used to stream audio files over HTTP";
				status obsolete;
			}

			enum "icloud" {
				opd:help "iCloud is a cloud computing service developed by Apple Inc. which allows to store and share data, from an iOS mobile (iPhone, iPad, iPod Touch) or a Macintosh";
				status obsolete;
			}

			enum "icmp6" {
				opd:help "ICMPv6 is the diagnostic protocol used in IPv6 networks";
				status obsolete;
			}

			enum "icq2go" {
				opd:help "This classifies the HTTP traffic to the hosts icq.com and icq.net";
				status obsolete;
			}

			enum "icrt" {
				opd:help "Cuban institute of radio and television website";
				status obsolete;
			}

			enum "icy" {
				opd:help "ICY is the former version of the SHOUTCast streaming protocol, developed by Nullsoft";
				status obsolete;
			}

			enum "id_net" {
				opd:help "Id.net is highly secure login system used for managing accounts for multiple websites";
				status obsolete;
			}

			enum "ident" {
				opd:help "The Identification Protocol provides a means to determine the identity of a user of a specific TCP connection";
				status obsolete;
			}

			enum "idnes" {
				opd:help "Czech news portal";
				status obsolete;
			}

			enum "idokep" {
				opd:help "Hungarian famous weather forecast website";
				status obsolete;
			}

			enum "idpr" {
				opd:help "The idpr protocol (Inter_Domain Policy Routing Protocol) is found over the IP layer (IANA protocol number: 35)";
				status obsolete;
			}

			enum "idpr_cmtp" {
				opd:help "The idpr_cmtp protocol (IDPR Control Message Transport Proto) is found over the IP layer (IANA protocol number: 38)";
				status obsolete;
			}

			enum "idrp" {
				opd:help "The idrp protocol (Inter_Domain Routing Protocol) is found over the IP layer (IANA protocol number: 45)";
				status obsolete;
			}

			enum "ifeng" {
				opd:help "New media company providing premium content on an integrated platform across Internet, mobile and TV channels in China";
				status obsolete;
			}

			enum "ifeng_finance" {
				opd:help "Ifeng finance news portal";
				status obsolete;
			}

			enum "ifile_it" {
				opd:help "Filecloud is a free cloud storage and content delivery web service";
				status obsolete;
			}

			enum "ifilmtv" {
				opd:help "iFilmTV is an Iranian television portal, featuring Live TV streaming";
				status obsolete;
			}

			enum "ifmp" {
				opd:help "The ifmp protocol (Ipsilon Flow Management Protocol) is found over the IP layer (IANA protocol number: 101)";
				status obsolete;
			}

			enum "ifolder_ru" {
				opd:help "Classifies web browsing on the ifolder.ru Direct DownLoad links service";
				status obsolete;
			}

			enum "igihe" {
				opd:help "Rwandan news website";
				status obsolete;
			}

			enum "igmp" {
				opd:help "The Internet Group Management Protocol (IGMP) is used by IP hosts to report their multicast group membership to routers";
				status obsolete;
			}

			enum "igp" {
				opd:help "The igp protocol (any private interior gateway (used by Cisco for their IGRP)) is found over the IP layer (IANA protocol number: 9)";
				status obsolete;
			}

			enum "iheartradio" {
				opd:help "iHeartRadio is an Internet radio service owned by iHeartMedia";
				status obsolete;
			}

			enum "iiop" {
				opd:help "IIOP is the GIOP implementation over TCP";
				status obsolete;
			}

			enum "ikea" {
				opd:help "This classifies the HTTP and SSL traffic to the host ikea.com";
				status obsolete;
			}

			enum "ikman" {
				opd:help "SriLankan free online classified ads";
				status obsolete;
			}

			enum "ikon" {
				opd:help "Mongolian free news portal site";
				status obsolete;
			}

			enum "ikub" {
				opd:help "Albanian web portal";
				status obsolete;
			}

			enum "il" {
				opd:help "The il protocol (IL Transport Protocol) is found over the IP layer (IANA protocol number: 40)";
				status obsolete;
			}

			enum "ilivid" {
				opd:help "Browser toolbar search engine and video player";
				status obsolete;
			}

			enum "iloveim" {
				opd:help "This classifies the HTTP traffic to the host iloveim.com";
				status obsolete;
			}

			enum "iltalehti" {
				opd:help "Finnish news portal";
				status obsolete;
			}

			enum "iltasanomat" {
				opd:help "Finnish news portal";
				status obsolete;
			}

			enum "imageshack" {
				opd:help "On-line free image sharing service";
				status obsolete;
			}

			enum "imap" {
				opd:help "The IMAP protocol (Internet Message Access Protocol Version 4) enables a client to access and manipulate electronic mail messages on a server";
				status obsolete;
			}

			enum "imaps" {
				opd:help "IMAPS is the secure version of the IMAP protocol";
				status obsolete;
			}

			enum "imdb" {
				opd:help "On-line information database related to movies and TV-shows";
				status obsolete;
			}

			enum "imeem" {
				opd:help "This classifies the HTTP traffic to the host imeem.com";
				status obsolete;
			}

			enum "imeet" {
				opd:help "On-line video-conferencing service using cloud-based technology";
				status obsolete;
			}

			enum "imesh" {
				opd:help "iMesh is a peer-to-peer protocol";
				status obsolete;
			}

			enum "imessage_file_download" {
				opd:help "Apple Web Service used to retrieve video messages sent between two iOS devices via the iMessage application";
				status obsolete;
			}

			enum "imgur" {
				opd:help "A free online image hosting service";
				status obsolete;
			}

			enum "iminent" {
				opd:help "Website providing add-ons for most messengers";
				status obsolete;
			}

			enum "imo" {
				opd:help "IMO is an instant messaging application which allows the users to exchange messages without having to pay for SMS, share photos and videos";
				status obsolete;
			}

			enum "imp" {
				opd:help "IMP is the IMAP webmail of the Horde project";
				status obsolete;
			}

			enum "impress" {
				opd:help "Japanese IT news website";
				status obsolete;
			}

			enum "imvu" {
				opd:help "This classifies the HTTP traffic to the host imvu.com";
				status obsolete;
			}

			enum "imyanmarhouse" {
				opd:help "Classified ads website in Myanmar";
				status obsolete;
			}

			enum "inbox" {
				opd:help "Latvian webmail and web portal";
				status obsolete;
			}

			enum "incomplete" {
				opd:help "Incomplete is used when the protocol signature is too long";
				status obsolete;
			}

			enum "indaba_music" {
				opd:help "This classifies the HTTP traffic to the host indabamusic.com";
				status obsolete;
			}

			enum "indeksonline" {
				opd:help "Albanian news portal";
				status obsolete;
			}

			enum "independent" {
				opd:help "Irish news portal";
				status obsolete;
			}

			enum "index_hr" {
				opd:help "Croatian web portal";
				status obsolete;
			}

			enum "index_hu" {
				opd:help "Hungarian web portal";
				status obsolete;
			}

			enum "indexexchange" {
				opd:help "Index Exchange (Casale Media) is a Canadian online advertising technology provider";
				status obsolete;
			}

			enum "indiatimes" {
				opd:help "Indiatimes is a popular Internet and mobile value-added services web portal in India";
				status obsolete;
			}

			enum "indonetwork" {
				opd:help "This classifies the HTTP traffic to the host indonetwork.co.id";
				status obsolete;
			}

			enum "indowebster" {
				opd:help "Indowebster.com or idws.id is an Indonesian website";
				status obsolete;
			}

			enum "inewsmalta" {
				opd:help "News webportal in Malta";
				status obsolete;
			}

			enum "infinity_blade_ii" {
				opd:help "Mobile game";
				status obsolete;
			}

			enum "infobae" {
				opd:help "News website located in Argentina";
				status obsolete;
			}

			enum "informix" {
				opd:help "Informix is a family of relational database management systems developed by IBM";
				status obsolete;
			}

			enum "ing" {
				opd:help "ING online banking website";
				status obsolete;
			}

			enum "inilah" {
				opd:help "This classifies the traffic to the host inilah.com";
				status obsolete;
			}

			enum "inmobi" {
				opd:help "InMobi provides advertising services for mobile platforms";
				status obsolete;
			}

			enum "inneractive" {
				opd:help "Inneractive is a monetizer for cross-platform mobile applications";
				status obsolete;
			}

			enum "innfrad" {
				opd:help "News website in Egypt";
				status obsolete;
			}

			enum "innovid" {
				opd:help "Innovid is a video platform for advertisers to measure video experience (QoE) on several devices";
				status obsolete;
			}

			enum "inquirer" {
				opd:help "Philippino news portal";
				status obsolete;
			}

			enum "instagram" {
				opd:help "Instagram is an online mobile photo-sharing and social networking service";
				status obsolete;
			}

			enum "intalking" {
				opd:help "Taiwanese beauty, makeup portal";
				status obsolete;
			}

			enum "interia" {
				opd:help "Polish news portal";
				status obsolete;
			}

			enum "internations" {
				opd:help "This classifies the HTTP traffic to the host internations.org";
				status obsolete;
			}

			enum "internet_org" {
				opd:help "Internet.org is a partnership between social networking services company Facebook and six companies (Samsung, Ericsson, MediaTek, Opera Software, Nokia and Qualcomm) that plans to bring affordable access to selected Internet services to less developed countries by increasing efficiency, and facilitating the development of new business models around the provision of Internet access";
				status obsolete;
			}

			enum "interpark" {
				opd:help "This classifies the HTTP traffic to the host www.interpark.com";
				status obsolete;
			}

			enum "intuit" {
				opd:help "This classifies the HTTP traffic to the host intuit.com";
				status obsolete;
			}

			enum "investigator" {
				opd:help "(Deprecated) Ugandan news portal";
				status obsolete;
			}

			enum "inwi" {
				opd:help "Moroccan mobile operator website";
				status obsolete;
			}

			enum "inyarwanda" {
				opd:help "Generic web portal in Rwanda, featuring news, music, photos, videos, etc";
				status obsolete;
			}

			enum "iodine" {
				opd:help "Iodine is a solution which provides tunneling through the standard DNS protocol";
				status obsolete;
			}

			enum "ios_ota_update" {
				opd:help "iOS OTA Update is the protocol used for iOS updates Over The Air";
				status obsolete;
			}

			enum "ip_exp_1" {
				opd:help "The ip_exp_1 protocol (IANA Internet Protocol Number 253 used for experimentation and testing) is found over the IP layer (IANA protocol number: 253)";
				status obsolete;
			}

			enum "ip_exp_2" {
				opd:help "The ip_exp_2 protocol (IANA Internet Protocol Number 254 used for experimentation and testing) is found over the IP layer (IANA protocol number: 254)";
				status obsolete;
			}

			enum "ip_in_ip" {
				opd:help "The ip_in_ip protocol (IP_within_IP Encapsulation Protocol) is found over the IP layer (IANA protocol number: 94)";
				status obsolete;
			}

			enum "ip_rdp" {
				opd:help "The ip_rdp protocol (Reliable Data Protocol over IP) is found over the IP layer (IANA protocol number: 27)";
				status obsolete;
			}

			enum "ip_reserved" {
				opd:help "The ip_reserved protocol (IANA Reserved Internet Protocol Number) is found over the IP layer (IANA protocol number: 255)";
				status obsolete;
			}

			enum "ipcomp" {
				opd:help "The ipcomp protocol (IP Payload Compression Protocol) is found over the IP layer (IANA protocol number: 108)";
				status obsolete;
			}

			enum "ipcp" {
				opd:help "The IP Control Protocol (IPCP) is used to configure IP parameters of a station on a Point To Point link";
				status obsolete;
			}

			enum "ipcv" {
				opd:help "The ipcv protocol (Internet Packet Core Utility) is found over the IP layer (IANA protocol number: 71)";
				status obsolete;
			}

			enum "iperf" {
				opd:help "The iPerf protocol is used by the self-titled tool for network performance measures";
				status obsolete;
			}

			enum "iplt" {
				opd:help "The iplt protocol (IPDS MES Physical Layer Tester) is found over the IP layer (IANA protocol number: 129)";
				status obsolete;
			}

			enum "ipp" {
				opd:help "Internet Printing Protocol (IPP) is a standard used for remote printing using Internet tools and technologies";
				status obsolete;
			}

			enum "ippc" {
				opd:help "The ippc protocol (Internet Pluribus Packet Core) is found over the IP layer (IANA protocol number: 67)";
				status obsolete;
			}

			enum "ipsec" {
				opd:help "The IPsec protocol suite includes Encapsulation Security Payload (ESP) and Authentication Header (AH) protocols";
				status obsolete;
			}

			enum "iptm" {
				opd:help "The iptm protocol (Protocol Internet Protocol Traffic Manager) is found over the IP layer (IANA protocol number: 84)";
				status obsolete;
			}

			enum "ipv6cp" {
				opd:help "This Protocol is used for establishing and configuring IPv6 over PPP";
				status obsolete;
			}

			enum "ipx_in_ip" {
				opd:help "The ipx_in_ip protocol (IPX in IP) is found over the IP layer (IANA protocol number: 111)";
				status obsolete;
			}

			enum "ipxrip" {
				opd:help "RIPIPX is the equivalent of the RIP protocol in Novell networks";
				status obsolete;
			}

			enum "ipxsap" {
				opd:help "Service Advertisement Protocol (SAP) allows servers to advertise their services to clients in a Novell network";
				status obsolete;
			}

			enum "iqiyi" {
				opd:help "Online video publishing platform very popular in China";
				status obsolete;
			}

			enum "irc" {
				opd:help "IRC (Internet Relay Chat) is an instant messaging protocol";
				status obsolete;
			}

			enum "irc_galleria" {
				opd:help "This classifies the HTTP traffic to the host irc-galleria.net";
				status obsolete;
			}

			enum "irc_transfer" {
				opd:help "This protocol is used to transport data in IRC file transfer";
				status obsolete;
			}

			enum "ircs" {
				opd:help "IRCs is the secure version of the IRC protocol";
				status obsolete;
			}

			enum "irctc" {
				status obsolete;
			}

			enum "irods" {
				opd:help "iRODS (Integrated Rule-Oriented Data System) is an open source data management software";
				status obsolete;
			}

			enum "irtp" {
				opd:help "The irtp protocol (Internet Reliable Transaction) is found over the IP layer (IANA protocol number: 28)";
				status obsolete;
			}

			enum "isakmp" {
				opd:help "The Internet Security Association and Key Management Protocol (ISAKMP) defines procedures and packet formats to establish, negotiate, modify and delete Security Associations (SA)";
				status obsolete;
			}

			enum "iscsi" {
				opd:help "Internet Small Computer Systems Interface (iSCSI), as described in RFC3720";
				status obsolete;
			}

			enum "isis" {
				opd:help "The isis protocol (ISIS for ipv4) is found over the IP layer (IANA protocol number: 124)";
				status obsolete;
			}

			enum "isl" {
				opd:help "InterSwitch Link Frame Format is a Cisco proprietary protocol used between network equipment of a LAN to transmit VLAN membership information of a frame";
				status obsolete;
			}

			enum "iso_ip" {
				opd:help "The iso_ip protocol (ISO Internet Protocol) is found over the IP layer (IANA protocol number: 80)";
				status obsolete;
			}

			enum "iso_tp4" {
				opd:help "The iso_tp4 protocol (ISO Transport Protocol Class 4) is found over the IP layer (IANA protocol number: 29)";
				status obsolete;
			}

			enum "issuu" {
				opd:help "Digital publishing website";
				status obsolete;
			}

			enum "isup" {
				opd:help "ISUP (ISDN User Part) is a telephony protocol used in SS7 networks";
				status obsolete;
			}

			enum "italki" {
				opd:help "This classifies the HTTP traffic to the host italki.com";
				status obsolete;
			}

			enum "itsmy" {
				opd:help "Itsmy.com is a social network and community site with the typical features such as profiles, forums, media-sharing and chat";
				status obsolete;
			}

			enum "itsup" {
				opd:help "Itsup tracks, analyzes and optimizes online advertising campaigns in real-time";
				status obsolete;
			}

			enum "itunes" {
				opd:help "iTunes is an Apple proprietary digital media player application, used for playing and organizing digital music and video files";
				status obsolete;
			}

			enum "itv_player" {
				opd:help "Proprietary iOS application and website for VOD content (TV catch up) and live channels streaming";
				status obsolete;
			}

			enum "iwarp" {
				opd:help "IWARP (Internet Wide Area RDMA Protocol) is a protocol suite that implements Remote Direct Memory Access for efficient data transfer";
				status obsolete;
			}

			enum "iwiw" {
				opd:help "This classifies the HTTP traffic to the host iwiw.hu";
				status obsolete;
			}

			enum "ja" {
				opd:help "Icelandic web portal";
				status obsolete;
			}

			enum "jabber" {
				opd:help "Jabber is an open standard instant messaging and presence system involving the XMPP protocol";
				status obsolete;
			}

			enum "jabber_transfer" {
				opd:help "Jabber transfer is an open standard to transfer file between two Jabber clients";
				status obsolete;
			}

			enum "jaiku" {
				opd:help "This classifies the HTTP traffic to the host jaiku.com";
				status obsolete;
			}

			enum "jajah" {
				opd:help "(Deprecated) Jajah was a VoIP provider owned by Telefonica Europe; Telefonica has shut down Jajah on January 31, 2014";
				status obsolete;
			}

			enum "jamaica_gleaner" {
				opd:help "Jamaican news portal";
				status obsolete;
			}

			enum "jamaicaobserver" {
				opd:help "Jamaican news portal";
				status obsolete;
			}

			enum "jamiiforums" {
				opd:help "Tanzanian forum and blog hosting site";
				status obsolete;
			}

			enum "jammerdirect" {
				opd:help "This classifies the HTTP traffic to the host jammerdirect.com";
				status obsolete;
			}

			enum "jango" {
				opd:help "This classifies the HTTP traffic to the host jango.com";
				status obsolete;
			}

			enum "jap" {
				opd:help "VPN/Anonymizer application";
				status obsolete;
			}

			enum "jasmin" {
				opd:help "Jasmin is an adult webcams website";
				status obsolete;
			}

			enum "java_rmi" {
				opd:help "Classifies the Java Remote Method Invocation (RMI) protocol";
				status obsolete;
			}

			enum "java_update" {
				opd:help "Java Update is the protocol for the update of the java virtual machines, also called JVM";
				status obsolete;
			}

			enum "javedch" {
				opd:help "News web portal in Bahrain";
				status obsolete;
			}

			enum "javhd" {
				opd:help "JAVHD is an Asian adult website";
				status obsolete;
			}

			enum "jawabkom" {
				opd:help "Question and answer web service in the Arab World";
				status obsolete;
			}

			enum "jawharafm" {
				opd:help "Tunisian news and multimedia website";
				status obsolete;
			}

			enum "jedi" {
				opd:help "JEDI is the name of the CITRIX streaming connection protocol";
				status obsolete;
			}

			enum "jetaoshqef" {
				opd:help "Albanian site providing viral news and humorous facts";
				status obsolete;
			}

			enum "jetdirect" {
				opd:help "The Jetdirect protocol is used by HP network printers";
				status obsolete;
			}

			enum "jfranews" {
				opd:help "New portal popular in Jordan and Palestinian Territory";
				status obsolete;
			}

			enum "jibjab" {
				opd:help "Video streaming website";
				status obsolete;
			}

			enum "jingdong" {
				opd:help "Popular Chinese on-line hi-tech shop";
				status obsolete;
			}

			enum "jira" {
				opd:help "This classifies the HTTP traffic to the host onjira.com";
				status obsolete;
			}

			enum "jne" {
				opd:help "This classifies the HTTP traffic to the host jne.co.id";
				status obsolete;
			}

			enum "jobs_af" {
				opd:help "Online job search in Afghanistan";
				status obsolete;
			}

			enum "jobs_bg" {
				opd:help "Bulgarian online job search";
				status obsolete;
			}

			enum "jobsdb" {
				opd:help "Job seeking website";
				status obsolete;
			}

			enum "jobstreet" {
				opd:help "This classifies the traffic to the host jobstreet.co.id";
				status obsolete;
			}

			enum "jofogas" {
				opd:help "Hungarian classified ads website";
				status obsolete;
			}

			enum "joongang_daily" {
				opd:help "This classifies the HTTP traffic to the hosts joins.com and joinsmsn.com and the SSL traffic to the host joins.com";
				status obsolete;
			}

			enum "joq" {
				opd:help "(Deprecated) Entertainment blog articles from Albania";
				status obsolete;
			}

			enum "jquery" {
				opd:help "jQuery is a javascript library";
				status obsolete;
			}

			enum "jubii" {
				opd:help "This classifies the HTTP and SSL traffic to the host jubii.dk";
				status obsolete;
			}

			enum "jumia" {
				opd:help "Popular online shopping website in Kenya and Ivory Coast";
				status obsolete;
			}

			enum "junkmail" {
				opd:help "South African classified ads website";
				status obsolete;
			}

			enum "justin_tv" {
				opd:help "(Deprecated) Justin.tv was a video-on-demand platform";
				status obsolete;
			}

			enum "jutarnji" {
				opd:help "Croatian news portal";
				status obsolete;
			}

			enum "jxta" {
				opd:help "Open source peer-to-peer protocol launched by Sun Microsystems";
				status obsolete;
			}

			enum "kaieteurnewsonline" {
				opd:help "Guyanese newspaper blog";
				status obsolete;
			}

			enum "kaioo" {
				opd:help "This classifies the HTTP traffic to the host kaioo.com";
				status obsolete;
			}

			enum "kaixin_chat" {
				opd:help "This classifies the traffic to the host kaixin001.com";
				status obsolete;
			}

			enum "kajgana" {
				opd:help "Macedonian news portal";
				status obsolete;
			}

			enum "kakaku" {
				opd:help "Website dedicated to price comparisons and product tests";
				status obsolete;
			}

			enum "kakaocdn" {
				opd:help "Kakaocdn is content delivery network used by KakaoTalk and KakaoStory";
				status obsolete;
			}

			enum "kakaostory" {
				opd:help "KakaoStory is a photo sharing social networking service for KakaoTalk users";
				status obsolete;
			}

			enum "kakaotalk" {
				opd:help "KakaoTalk is an instant messaging platform for mobile devices; users or group of users can send messages, share photos, videos and contact information";
				status obsolete;
			}

			enum "kalerkantho" {
				opd:help "Bangladeshi news portal";
				status obsolete;
			}

			enum "kankan" {
				opd:help "Chinese video streaming website";
				status obsolete;
			}

			enum "kapanlagi" {
				opd:help "Kapanlagi Network is an Indonesian media group";
				status obsolete;
			}

			enum "kapook" {
				opd:help "Thailandese web portal";
				status obsolete;
			}

			enum "karosgame" {
				opd:help "Online multiplayer game popular in Russia";
				status obsolete;
			}

			enum "kaskus" {
				opd:help "Kaskus is an Indonesian forum hosting platform";
				status obsolete;
			}

			enum "kaspersky" {
				opd:help "This classifies the HTTP traffic to the host kaspersky.com";
				status obsolete;
			}

			enum "kaspersky_update" {
				opd:help "Kaspersky_update is the protocol used for Kaspersky software updates";
				status obsolete;
			}

			enum "kasvyksta" {
				opd:help "Web news portal about cultural events happening in Lithuania";
				status obsolete;
			}

			enum "kazaa" {
				opd:help "KaZaA is a peer-to-peer protocol";
				status obsolete;
			}

			enum "kb_bank" {
				opd:help "Website of a bank in South Korea";
				status obsolete;
			}

			enum "kbn_live" {
				opd:help "Breaking news website in Cambodia";
				status obsolete;
			}

			enum "kbs" {
				opd:help "KBS is a national public broadcaster in South Korea, operating radio, television and online services";
				status obsolete;
			}

			enum "kbstar" {
				opd:help "(Deprecated) This web service is closed";
				status obsolete;
			}

			enum "keezmovies" {
				opd:help "Adult movie streaming website";
				status obsolete;
			}

			enum "kemenkumham" {
				opd:help "Website of the Ministry of Justice and Human Rights of the Republic of Indonesia";
				status obsolete;
			}

			enum "khaberni" {
				opd:help "Jordanian news portal";
				status obsolete;
			}

			enum "khan" {
				opd:help "Korean news web portal";
				status obsolete;
			}

			enum "khmer_news" {
				opd:help "Cambodian news portal";
				status obsolete;
			}

			enum "khmer_note" {
				opd:help "Cambodian website about different topics including current news and lifestyle";
				status obsolete;
			}

			enum "khmer_press" {
				opd:help "Cambodian website about different topics including current news and lifestyle";
				status obsolete;
			}

			enum "khmeread" {
				opd:help "Cambodian news portal";
				status obsolete;
			}

			enum "khmerload" {
				opd:help "Cambodian web portal";
				status obsolete;
			}

			enum "kickasstorrents" {
				opd:help "Kickass Torrents is a popular torrent and magnet search engine";
				status obsolete;
			}

			enum "kigalitoday" {
				opd:help "Rwandese news portal";
				status obsolete;
			}

			enum "kijiji" {
				opd:help "Canadian free local classifieds";
				status obsolete;
			}

			enum "kik" {
				opd:help "KIK Messenger is a Chinese Instant Messaging service";
				status obsolete;
			}

			enum "king" {
				opd:help "King is a mobile game editor";
				status obsolete;
			}

			enum "kingdomxxx" {
				opd:help "BitTorrent tracker search engine";
				status obsolete;
			}

			enum "kino" {
				opd:help "(Deprecated) This classifies the HTTP traffic to the host kino.to";
				status obsolete;
			}

			enum "kinogo" {
				opd:help "Pirate movie streaming and download blog popular in Armenia";
				status obsolete;
			}

			enum "kiwibox" {
				opd:help "Kiwibox is a social network, featuring mobile applications";
				status obsolete;
			}

			enum "klikbca" {
				opd:help "Internet banking service of the Bank Central Asia (BCA)";
				status obsolete;
			}

			enum "klix" {
				opd:help "Bosnian news portal";
				status obsolete;
			}

			enum "koha" {
				opd:help "Albanian news portal";
				status obsolete;
			}

			enum "kohsantepheapdaily" {
				opd:help "Cambodian news portal";
				status obsolete;
			}

			enum "kolektiv" {
				opd:help "Montenegrien website on media and lifestyle";
				status obsolete;
			}

			enum "kompas" {
				opd:help "Indonesian national newspaper web portal";
				status obsolete;
			}

			enum "kompasiana" {
				opd:help "Blog platform provider and blog directory in Indonesia";
				status obsolete;
			}

			enum "konaminet" {
				opd:help "This classifies the HTTP traffic to the host konaminet.jp";
				status obsolete;
			}

			enum "konga" {
				opd:help "Nigerian online shopping website";
				status obsolete;
			}

			enum "koolim" {
				opd:help "This classifies the HTTP traffic to the host koolim.com";
				status obsolete;
			}

			enum "kooora" {
				opd:help "Arabic sports news portal";
				status obsolete;
			}

			enum "kpasswd" {
				opd:help "kpasswd is the protocol used to change a Kerberos password";
				status obsolete;
			}

			enum "kproxy" {
				opd:help "KProxy is an anonymizing proxy used for private browsing, firewall bypassing and evasion";
				status obsolete;
			}

			enum "krb5" {
				opd:help "Kerberos provides a means to verify the identities of the different workstations on an open (unprotected) network";
				status obsolete;
			}

			enum "krux" {
				opd:help "Krux is a data management company whose services not only includes data security but also (and this is where krxd comes in) visitor tracking and monetization services";
				status obsolete;
			}

			enum "kryptolan" {
				opd:help "The kryptolan protocol (Kryptolan) is found over the IP layer (IANA protocol number: 65)";
				status obsolete;
			}

			enum "kstna" {
				opd:help "Jordanian job offer website";
				status obsolete;
			}

			enum "ku6" {
				opd:help "Ku6 Media, an online video company";
				status obsolete;
			}

			enum "kuenselonline" {
				opd:help "Bhutanese news portal";
				status obsolete;
			}

			enum "kugou" {
				opd:help "Kugou is a multimedia peer-to-peer application providing file sharing, chat or broadcasting services";
				status obsolete;
			}

			enum "kundo" {
				opd:help "Kundo offers simple and powerful tools for customer service";
				status obsolete;
			}

			enum "kupujemprodajem" {
				opd:help "Serbian classified ads website";
				status obsolete;
			}

			enum "kurir" {
				opd:help "Serbian news portal";
				status obsolete;
			}

			enum "kurir_info" {
				opd:help "Serbian news portal";
				status obsolete;
			}

			enum "kuxun" {
				opd:help "Chinese travel website";
				status obsolete;
			}

			enum "kwejk" {
				opd:help "Polish multimedia website";
				status obsolete;
			}

			enum "laacibnet" {
				opd:help "Sports news portal dedicated to football in Somalia";
				status obsolete;
			}

			enum "labanquepostale" {
				opd:help "French bank offering insurance and banking services";
				status obsolete;
			}

			enum "lady8844" {
				opd:help "Chinese fashion and beauty website";
				status obsolete;
			}

			enum "lajmi" {
				opd:help "Albanian news portal";
				status obsolete;
			}

			enum "lan" {
				opd:help "The lan protocol (Any local network) is found over the IP layer (IANA protocol number: 63)";
				status obsolete;
			}

			enum "lanacion" {
				opd:help "Argentinian news portal";
				status obsolete;
			}

			enum "lankadeepa" {
				opd:help "SriLankan news portal";
				status obsolete;
			}

			enum "lanshark" {
				opd:help "Lanshark is a p2p client for LAN";
				status obsolete;
			}

			enum "lapagina" {
				opd:help "El Salvadorian news portal";
				status obsolete;
			}

			enum "lapatilla" {
				opd:help "Venezuelan news portal";
				status obsolete;
			}

			enum "laposte_webmail" {
				opd:help "Laposte Webmail is a webmail protocol";
				status obsolete;
			}

			enum "laprensa" {
				opd:help "Nicaraguan news portal, also accessed from Honduras";
				status obsolete;
			}

			enum "laprensagrafica" {
				opd:help "El Salvadorian news portal";
				status obsolete;
			}

			enum "laredoute" {
				opd:help "La Redoute is a French multi-channel retailer";
				status obsolete;
			}

			enum "larp" {
				opd:help "The larp protocol (Locus Address Resolution Protocol) is found over the IP layer (IANA protocol number: 91)";
				status obsolete;
			}

			enum "lastfm" {
				opd:help "Last.fm is a web-radio service, featuring a music recommender system (called Audioscrobbler)";
				status obsolete;
			}

			enum "lastpass" {
				opd:help "Password manager application";
				status obsolete;
			}

			enum "lativ" {
				opd:help "Taiwanese online clothes shop";
				status obsolete;
			}

			enum "lava_lava" {
				opd:help "Lava Lava is a Chinese language based Instant Messaging application";
				status obsolete;
			}

			enum "lazada" {
				opd:help "Online shopping mall popular in Southeast Asia";
				status obsolete;
			}

			enum "lcp" {
				opd:help "LCP is used to establish, configure and test the data-link connection for a PPP link";
				status obsolete;
			}

			enum "ldap" {
				opd:help "LDAP (Lightweight Directory Access Protocol) is a protocol used for accessing directory services";
				status obsolete;
			}

			enum "ldaps" {
				opd:help "Secure LDAP is the Secure version of the LDAP protocol";
				status obsolete;
			}

			enum "ldblog" {
				opd:help "Japanese blog dedicated to IT and Hacking";
				status obsolete;
			}

			enum "le360" {
				opd:help "Infotainment website in Morocco";
				status obsolete;
			}

			enum "leaf_1" {
				opd:help "The leaf_1 protocol (Leaf 1) is found over the IP layer (IANA protocol number: 25)";
				status obsolete;
			}

			enum "leaf_2" {
				opd:help "The leaf_2 protocol (Leaf 2) is found over the IP layer (IANA protocol number: 26)";
				status obsolete;
			}

			enum "leapfile" {
				opd:help "LeapFILE is a professional secured file sending and delivery web service";
				status obsolete;
			}

			enum "leboncoin" {
				opd:help "Leboncoin is a French classified ads website";
				status obsolete;
			}

			enum "lefaso" {
				opd:help "News website in Burkina Faso";
				status obsolete;
			}

			enum "lent" {
				opd:help "Azerbaijani news portal";
				status obsolete;
			}

			enum "leral" {
				opd:help "Senegalese news portal";
				status obsolete;
			}

			enum "leteckaposta_cz" {
				opd:help "Classifies web browsing on the leteckaposta.cz Direct DownLoad links service";
				status obsolete;
			}

			enum "letv" {
				opd:help "letv.com is a Chinese online video portal";
				status obsolete;
			}

			enum "level3" {
				opd:help "Official website of Level 3 Communications, an American multinational Tier 1 telecom";
				status obsolete;
			}

			enum "lexpress" {
				opd:help "Mauritian news portal";
				status obsolete;
			}

			enum "lg_eshop" {
				opd:help "Chinese shopping portal for LG electronic products";
				status obsolete;
			}

			enum "libero_video" {
				opd:help "Italian web portal, providing news, e-mail, web-hosting, and more";
				status obsolete;
			}

			enum "libjingle_pseudotcp" {
				opd:help "This signature classifies Pseudo Tcp used by the libjingle on PC as well as on Mobile";
				status obsolete;
			}

			enum "librarything" {
				opd:help "LibraryThing is a social web application for storing and sharing book catalogs and various types of book metadata";
				status obsolete;
			}

			enum "lider_bet" {
				opd:help "Georgian online betting and gaming platform";
				status obsolete;
			}

			enum "life" {
				opd:help "Taiwanese media and lifestyle website";
				status obsolete;
			}

			enum "lifeknot" {
				opd:help "LifeKnot is a social network with a focus on shared interests and hobbies";
				status obsolete;
			}

			enum "liftoff" {
				opd:help "Liftoff is a mobile app marketing and retargeting platform";
				status obsolete;
			}

			enum "ligatus" {
				opd:help "Ligatus provides advertising solutions for websites";
				status obsolete;
			}

			enum "lightstreamer" {
				opd:help "Lightstreamer is a real-time engine that delivers data over HTTP and WebSockets";
				status obsolete;
			}

			enum "line" {
				opd:help "Line is a Japanese Instant Messaging and VoIP application for smartphones and PCs";
				status obsolete;
			}

			enum "line_games" {
				opd:help "This classifies the HTTP traffic to the host linegame.jp, the portal of various Line games";
				status obsolete;
			}

			enum "line_wind_runner" {
				opd:help "Line Wind Runner is a popular Asian mobile device game accessible from the Line application";
				status obsolete;
			}

			enum "lineage2" {
				opd:help "Lineage2 is a MMORPG developed by NCSoft";
				status obsolete;
			}

			enum "linio" {
				opd:help "Latino American ecommerce portal";
				status obsolete;
			}

			enum "linkedin" {
				opd:help "LinkedIn is professional social network";
				status obsolete;
			}

			enum "lintasberita" {
				opd:help "This classifies the HTTP traffic to the hosts lintasberita.com and lintas.me";
				status obsolete;
			}

			enum "lionair" {
				opd:help "Lion Air is an Indonesian low-cost airline based in Jakarta, Indonesia";
				status obsolete;
			}

			enum "liontravel" {
				opd:help "Liontravel.com is the official website of Lion Travel Service which is a travel agency headquartered in Taipei";
				status obsolete;
			}

			enum "liputan6" {
				opd:help "Indonesian news portal";
				status obsolete;
			}

			enum "list_am" {
				opd:help "Armenian classified ads website";
				status obsolete;
			}

			enum "listindiario" {
				opd:help "Dominican republic news portal";
				status obsolete;
			}

			enum "listografy" {
				opd:help "Listography.com is a web application which allows its users to create and share lists";
				status obsolete;
			}

			enum "live_groups" {
				opd:help "Windows Live Groups is an online service by Microsoft that enables users to create their social groups for sharing, discussion and coordination";
				status obsolete;
			}

			enum "live_hotmail" {
				opd:help "Windows Live Hotmail is a free webmail service operated by Microsoft";
				status obsolete;
			}

			enum "live_meeting" {
				opd:help "Microsoft Office Live Meeting is a commercial subscription-based web conferencing service operated by Microsoft";
				status obsolete;
			}

			enum "live_mesh" {
				opd:help "Free on-line file storage and sharing service distributed by Microsoft";
				status obsolete;
			}

			enum "live_storage" {
				opd:help "(Deprecated) Windows Live File Storage is a Microsoft web service designed to be used by other Microsoft web services that may need storage, for example msn, skydrive, etc";
				status obsolete;
			}

			enum "livechat" {
				opd:help "LiveChat is an online customer service software with live support, help desk software and web analytics capabilities";
				status obsolete;
			}

			enum "livedoor" {
				opd:help "Livedoor.com is a Japanese web portal and blog platform";
				status obsolete;
			}

			enum "liveinternet" {
				opd:help "Liveinternet.ru is a web portal popular in the Russian Federation";
				status obsolete;
			}

			enum "livejournal" {
				opd:help "LiveJournal is a social networking service";
				status obsolete;
			}

			enum "livemail_attach" {
				opd:help "Detection of the Windows Live Mail file-attachment uploads";
				status obsolete;
			}

			enum "livemail_mobile" {
				opd:help "Livemail_mobile is the livemail webmail for mobile phones";
				status obsolete;
			}

			enum "livemocha" {
				opd:help "(Deprecated) This classifies the HTTP traffic to the host livemocha.com";
				status obsolete;
			}

			enum "liveperson" {
				opd:help "LivePerson develops products for online messaging, marketing, and analytics";
				status obsolete;
			}

			enum "liverail" {
				opd:help "This classifies LiveRail which is an online video advertising platform";
				status obsolete;
			}

			enum "livescore" {
				opd:help "Sports web portal providing real time football match scores";
				status obsolete;
			}

			enum "livingsocial" {
				opd:help "LivingSocialis an online marketplace focused on restaurant deals";
				status obsolete;
			}

			enum "lkqd" {
				opd:help "LKQD is a multi-screen video ad serving solution built specifically for publishers";
				status obsolete;
			}

			enum "llnwd" {
				opd:help "Content Delivery Network owned by the Limelight Networks company, providing media storage for several media content web services";
				status obsolete;
			}

			enum "llp" {
				opd:help "LLP is a protocol encapsulating messages";
				status obsolete;
			}

			enum "load_to" {
				opd:help "Classifies web browsing on the load.to Direct DownLoad links service";
				status obsolete;
			}

			enum "loadbalan" {
				opd:help "Load Balancing is a protocol used in the Windows environment to distribute traffic between servers";
				status obsolete;
			}

			enum "localytics" {
				opd:help "Localytics is an analytics and marketing platform for mobile and web apps";
				status obsolete;
			}

			enum "logmein" {
				opd:help "This signature detects generic connections to remote control, remote assistance and VPN servers managed by LogMeIn";
				status obsolete;
			}

			enum "logmein_rescue" {
				opd:help "Remote PC assistance software, accessible from web browser using a proprietary plug-in";
				status obsolete;
			}

			enum "lokalisten" {
				opd:help "German social networking website";
				status obsolete;
			}

			enum "lookout_ms" {
				opd:help "All-in-one security software for mobile devices";
				status obsolete;
			}

			enum "loop" {
				status obsolete;
			}

			enum "looppng" {
				opd:help "Main news and entertainment web portal in Papua New Guinea";
				status obsolete;
			}

			enum "lotame" {
				opd:help "Lotame is a web data analytics platform (aka Data Management Platform)";
				status obsolete;
			}

			enum "lotour" {
				opd:help "Chinese travel website";
				status obsolete;
			}

			enum "lotte" {
				opd:help "This classifies the HTTP traffic to the host lotte.com";
				status obsolete;
			}

			enum "lotterypost" {
				opd:help "Provides information about winning lottery numbers in the US";
				status obsolete;
			}

			enum "lotus_live" {
				opd:help "Lotus live, now IBM SmartCloud, is a web-based collaborative suite of applications for enterprises, including mail, file transfer, meetings and forms";
				status obsolete;
			}

			enum "lotus_sametime" {
				opd:help "IBM Lotus Sametime is a client-server application and middleware platform that provides real-time, unified communications and collaboration for enterprises";
				status obsolete;
			}

			enum "lotusnotes" {
				opd:help "Lotus Notes is a groupware knowledge management system which integrates various services such as web browsing, calendaring and mailing";
				status obsolete;
			}

			enum "lpr" {
				opd:help "LPR is a protocol providing printing services and used in Berkeley distributions of the Unix operating system";
				status obsolete;
			}

			enum "lqr" {
				opd:help "The Link Quality Report (LQR) protocol is a part of the Point-to-Point Protocol (PPP), which allows two computers to connect to each other";
				status obsolete;
			}

			enum "lrytas" {
				opd:help "Lithuanian news portal";
				status obsolete;
			}

			enum "ltn" {
				opd:help "Taiwanese news portal";
				status obsolete;
			}

			enum "ltt" {
				opd:help "Libya Telecom and Technology company website";
				status obsolete;
			}

			enum "luke" {
				opd:help "Luke is a P2P portal and software";
				status obsolete;
			}

			enum "lun" {
				opd:help "Chilean news and entertainment portal";
				status obsolete;
			}

			enum "lunarstorm" {
				opd:help "This classifies the HTTP traffic to the host lunarstorm.se";
				status obsolete;
			}

			enum "lusakatimes" {
				opd:help "News web portal in Zambia (politics, sports, health, etc.)";
				status obsolete;
			}

			enum "lvping" {
				opd:help "Chinese Hotel Reviews, Travel Guides, Forum and tourist guide";
				status obsolete;
			}

			enum "lync" {
				opd:help "Microsoft Skype for Business (formerly Microsoft Lync) IM, VoIP and desktop sharing services (corporate services)";
				status obsolete;
			}

			enum "lync_online" {
				opd:help "On-line version of the Microsoft Skype for Business (formerly Microsoft Lync) IM and VoIP services (Office 365)";
				status obsolete;
			}

			enum "lynda" {
				opd:help "Lynda.com is an online education company";
				status obsolete;
			}

			enum "m2pa" {
				opd:help "M2PA is a signaling peer-to-peer protocol used by MTP2 in the Signaling System 7 (SS7)";
				status obsolete;
			}

			enum "m2ua" {
				opd:help "M2UA is an SCTP adaptation layer for encapsulated MTP2 messages in the Signaling System 7 (SS7)";
				status obsolete;
			}

			enum "m3ua" {
				opd:help "M3UA enables SS7 protocols stacking (ISUP, SCCP, etc) over an IP network";
				status obsolete;
			}

			enum "maaii" {
				opd:help "Maaii is a cross-platform messaging application which allows iPhone and Android users to send and receive text messages and phone calls for free";
				status obsolete;
			}

			enum "maannews" {
				opd:help "Palestinian news portal";
				status obsolete;
			}

			enum "magicjack" {
				opd:help "MagicJack is a VoIP service for home and business use, available as a mobile application and also with a proprietary device (magicJack PLUS)";
				status obsolete;
			}

			enum "magumagu" {
				opd:help "2013 for Kakao (aka Magu-Magu) is Korean baseball game, developed by CJ E&M corp";
				status obsolete;
			}

			enum "mail2000" {
				opd:help "Taiwanese Webmail and SMS services";
				status obsolete;
			}

			enum "mail_189" {
				opd:help "China Telecom email services";
				status obsolete;
			}

			enum "mail_ru_games" {
				opd:help "Online gaming site";
				status obsolete;
			}

			enum "mail_ru_love" {
				opd:help "Love@Mail.Ru is a Russian dating website and mobile application";
				status obsolete;
			}

			enum "mail_ru_moimir" {
				opd:help "Social networking website";
				status obsolete;
			}

			enum "mail_ru_webagent" {
				opd:help "(Deprecated) Mail.ru custom web browser";
				status obsolete;
			}

			enum "mailru" {
				opd:help "Mail.ru is a Russian web portal providing services such as webmail, search engine, instant messaging";
				status obsolete;
			}

			enum "mailru_agent" {
				opd:help "Mail.ru Agent is a cross-platform mobile messaging application supporting text, audio and video";
				status obsolete;
			}

			enum "mako" {
				opd:help "Israeli news portal";
				status obsolete;
			}

			enum "maktoob" {
				opd:help "Maktoob is a webmail protocol";
				status obsolete;
			}

			enum "malformed" {
				opd:help "A packet belongs to the protocol 'malformed' if the protocol announced by the lower level protocol does not correspond to the one determined by the system";
				status obsolete;
			}

			enum "malijet" {
				opd:help "News web portal in Mali";
				status obsolete;
			}

			enum "maliweb" {
				opd:help "News and classified ads portal in Mali";
				status obsolete;
			}

			enum "maltapark" {
				opd:help "Maltapark is a popular trading website in Malta";
				status obsolete;
			}

			enum "maltatoday" {
				opd:help "Maltese news portal";
				status obsolete;
			}

			enum "mana" {
				opd:help "French Polynesian internet service provider website";
				status obsolete;
			}

			enum "mandriva_update" {
				opd:help "This protocol manages the mandriva update operations";
				status obsolete;
			}

			enum "manet" {
				opd:help "The manet protocol (MANET Protocols) is found over the IP layer (IANA protocol number: 138)";
				status obsolete;
			}

			enum "mangocity" {
				opd:help "Chinese Travel website";
				status obsolete;
			}

			enum "mangvieclam" {
				opd:help "Job seeking website in Vietnam";
				status obsolete;
			}

			enum "manolito" {
				opd:help "Manolito is a peer-to-peer file sharing software";
				status obsolete;
			}

			enum "manoramaonline" {
				opd:help "English and Malayalam language daily local news based in Kottayam";
				status obsolete;
			}

			enum "manx" {
				opd:help "Telecom provider on the Isle of Man, also providing a portal with news, classifieds, features, and jobs";
				status obsolete;
			}

			enum "mapbox" {
				opd:help "Mapbox is an open source mapping platform for custom designed maps";
				status obsolete;
			}

			enum "mapi" {
				opd:help "MS Exchange Message API is a protocol used by Exchange clients to retrieve their emails";
				status obsolete;
			}

			enum "mapquest" {
				opd:help "Free online web mapping service owned by AOL";
				status obsolete;
			}

			enum "mapy" {
				opd:help "Czech republic localization website";
				status obsolete;
			}

			enum "marca" {
				opd:help "Spanish sports news portal";
				status obsolete;
			}

			enum "marebpress" {
				opd:help "Yemeni news portal";
				status obsolete;
			}

			enum "marktplaats" {
				opd:help "Dutch advertising site where you can sell, new and second-hand goods";
				status obsolete;
			}

			enum "mashable" {
				opd:help "This classifies the HTTP traffic to the host mashable.com";
				status obsolete;
			}

			enum "mashare" {
				opd:help "(Deprecated) Mashare was an online solution to store, send and share files";
				status obsolete;
			}

			enum "match" {
				opd:help "This classifies the HTTP traffic to the host match.com";
				status obsolete;
			}

			enum "maxcdn" {
				opd:help "MaxCDN is a content delivery network (CDN) provider";
				status obsolete;
			}

			enum "maybank2u" {
				opd:help "Malay banking website";
				status obsolete;
			}

			enum "mbc" {
				opd:help "MBC (aka iMBC) is a South-Korean television and radio network";
				status obsolete;
			}

			enum "mbl" {
				opd:help "Icelandic news portal";
				status obsolete;
			}

			enum "mbn" {
				opd:help "This classifies the HTTP traffic to the host mbn.co.kr";
				status obsolete;
			}

			enum "mcafee" {
				opd:help "McAfee is one of the leaders in intrusion prevention and security risk management on the web";
				status obsolete;
			}

			enum "mcb_home" {
				opd:help "Curacaoan online web service of the MCB Bank";
				status obsolete;
			}

			enum "mcs" {
				opd:help "Multipoint Communication Service (MCS) is a multipoint data delivery service for use in multimedia and audiovisual conferencing service";
				status obsolete;
			}

			enum "mebc" {
				opd:help "The Middle East Broadcasting Center Group is a free-to-air TV broadcasting company in the Arab World";
				status obsolete;
			}

			enum "media_innovation_group" {
				opd:help "The Media Innovation Group is specialized in online digital advertising, search marketing";
				status obsolete;
			}

			enum "mediacongo" {
				opd:help "News and classified ads portal in the Democratic Republic of Congo";
				status obsolete;
			}

			enum "mediafire" {
				opd:help "This classifies the HTTP traffic to the hosts a.1521.x.akamai.net and mediafire.com";
				status obsolete;
			}

			enum "mediamath" {
				opd:help "MediaMath is a global provider of digital media and data management technology for advertisers and agencies";
				status obsolete;
			}

			enum "meerkat" {
				opd:help "(Deprecated) Meerkat was a mobile application allowing Twitter users to live stream video to their followers";
				status obsolete;
			}

			enum "meetin" {
				opd:help "MEETin.org is a web-based social community";
				status obsolete;
			}

			enum "meetingplace" {
				opd:help "MeetingPlace is a protocol used by the Cisco Unified MeetingPlace suite of voice, web, and video conferencing products";
				status obsolete;
			}

			enum "meetme" {
				opd:help "Social networking web-service available on PC and mobile devices";
				status obsolete;
			}

			enum "meettheboss" {
				opd:help "This classifies the HTTP and SSL traffic to the host meettheboss.tv";
				status obsolete;
			}

			enum "meetup" {
				opd:help "Meetup is an online social networking portal for offline group meetings";
				status obsolete;
			}

			enum "meevee" {
				opd:help "(Deprecated) Closed on-line video aggregator website";
				status obsolete;
			}

			enum "mega" {
				opd:help "MEGA is an online file sharing service from Kim Dotcom";
				status obsolete;
			}

			enum "megaproxy" {
				opd:help "Megaproxy is a free anonymous proxy surfing service";
				status obsolete;
			}

			enum "megashares_com" {
				opd:help "Classifies web browsing on the megashares.com Direct DownLoad links service";
				status obsolete;
			}

			enum "megaupload" {
				opd:help "(Deprecated) Megaupload was an online solution to store, send and share files";
				status obsolete;
			}

			enum "megavideo" {
				opd:help "(Deprecated) This classifies the HTTP traffic to the host megavideo.com";
				status obsolete;
			}

			enum "meituan" {
				opd:help "Chinese group buying website selling vouchers on local services and entertainment";
				status obsolete;
			}

			enum "mekusharim" {
				opd:help "Social network website";
				status obsolete;
			}

			enum "mendeley" {
				opd:help "Sharing and annotating document web service";
				status obsolete;
			}

			enum "menstylefashion" {
				opd:help "Website with fashion and lifestyle articles, popular in Andorra";
				status obsolete;
			}

			enum "mercadolibre" {
				opd:help "MercadoLibre is a technology company that provides e-commerce solutions";
				status obsolete;
			}

			enum "mercador" {
				opd:help "(Deprecated) Romanian classified ads portal";
				status obsolete;
			}

			enum "merit_inp" {
				opd:help "The merit_inp protocol (MERIT Internodal Protocol) is found over the IP layer (IANA protocol number: 32)";
				status obsolete;
			}

			enum "merojax" {
				opd:help "Armenian Internet Portal featuring TV Series, Shows, Movies, Music and Radio";
				status obsolete;
			}

			enum "merrjep" {
				opd:help "Kosovan classified ads";
				status obsolete;
			}

			enum "messengerfx" {
				opd:help "This classifies the HTTP traffic to the host messengerfx.com";
				status obsolete;
			}

			enum "metacafe" {
				opd:help "Metacafe is a popular video sharing website launched in 2002";
				status obsolete;
			}

			enum "mfe_nsp" {
				opd:help "The mfe_nsp protocol (MFE Network Services Protocol) is found over the IP layer (IANA protocol number: 31)";
				status obsolete;
			}

			enum "mgcp" {
				opd:help "MGCP protocol is used as signaling protocol for voice IP applications";
				status obsolete;
			}

			enum "mgid" {
				opd:help "MGID is an ad network";
				status obsolete;
			}

			enum "mgoon" {
				opd:help "Website providing video streaming, and online video gaming";
				status obsolete;
			}

			enum "miaopai" {
				opd:help "Miaopai is a mobile video app software editor based in China";
				status obsolete;
			}

			enum "mibbit" {
				opd:help "This classifies the HTTP traffic of any client for chat.mibbit.com";
				status obsolete;
			}

			enum "micp" {
				opd:help "The micp protocol (Mobile Internetworking Control Pro.) is found over the IP layer (IANA protocol number: 95)";
				status obsolete;
			}

			enum "microsoft" {
				opd:help "This signature classifies hosts owned by Microsoft";
				status obsolete;
			}

			enum "mihaaru" {
				opd:help "A trusted news source in the Maldives";
				status obsolete;
			}

			enum "mihanblog" {
				opd:help "Persian blogging platform";
				status obsolete;
			}

			enum "mihanwebads" {
				opd:help "Iranian Internet AD company website";
				status obsolete;
			}

			enum "mikogo" {
				opd:help "Mikogo is a free desktop sharing and web conferencing service";
				status obsolete;
			}

			enum "milad" {
				opd:help "Palestinian news portal";
				status obsolete;
			}

			enum "milanuncios" {
				opd:help "Spanish classified ads website";
				status obsolete;
			}

			enum "millardayo" {
				opd:help "Global news portal in Tanzania";
				status obsolete;
			}

			enum "milli" {
				opd:help "Azerbaijani news portal";
				status obsolete;
			}

			enum "milliyet" {
				opd:help "Turkish news portal";
				status obsolete;
			}

			enum "mimp" {
				opd:help "MIMP is the IMP webmail for mobile phones";
				status obsolete;
			}

			enum "minecraft_pocket" {
				opd:help "Minecraft Pocket is a game about placing blocks and going on adventures";
				status obsolete;
			}

			enum "mingpao" {
				opd:help "Web portal of a famous newspaper published in Hong Kong";
				status obsolete;
			}

			enum "minuto30" {
				opd:help "Colombian news portal";
				status obsolete;
			}

			enum "mipv6" {
				opd:help "Mobile IP is a proposed standard protocol that builds on the Internet Protocol by making mobility transparent to applications and higher level protocols like TCP";
				status obsolete;
			}

			enum "miro" {
				opd:help "Multimedia player";
				status obsolete;
			}

			enum "mistreci" {
				opd:help "Albanian movie streaming website";
				status obsolete;
			}

			enum "mitalk" {
				opd:help "MiTalk (aka Miliao) is a mobile instant messaging application from Xiaomi Tech";
				status obsolete;
			}

			enum "mixi" {
				opd:help "This classifies the HTTP traffic to the host mixi.jp";
				status obsolete;
			}

			enum "mixpanel" {
				opd:help "Mixpanel provides advertising services for mobile platforms";
				status obsolete;
			}

			enum "mk" {
				opd:help "This classifies the HTTP traffic to the host mk.co.kr";
				status obsolete;
			}

			enum "mmm_nigeria" {
				opd:help "Social Financial Network system web portal, famous in Nigeria";
				status obsolete;
			}

			enum "mms" {
				opd:help "MMS protocol is used extensively nowadays by Microsoft video streaming servers";
				status obsolete;
			}

			enum "mms_iso" {
				opd:help "ISO 9506 Manufacturing Message Specification (MMS)";
				status obsolete;
			}

			enum "mmse" {
				opd:help "The MultiMedia Messages Encapsulation protocol (MMSE) is used by mobile stations to send multimedia messages";
				status obsolete;
			}

			enum "moat" {
				opd:help "Moat is an analytics and intelligence company focused on transforming brand advertising online";
				status obsolete;
			}

			enum "mobage" {
				opd:help "Mobile games download portal and identification services";
				status obsolete;
			}

			enum "mobfox" {
				opd:help "Mobfox is a mobile advertising platform";
				status obsolete;
			}

			enum "mobile" {
				opd:help "The mobile protocol (IP Mobility) is found over the IP layer (IANA protocol number: 55)";
				status obsolete;
			}

			enum "mobile01" {
				opd:help "Taiwanese social network";
				status obsolete;
			}

			enum "mobile_me" {
				opd:help "(Deprecated) On-line web application suite (me.com) created by Apple and replaced by iCloud in 2011";
				status obsolete;
			}

			enum "mobilehdr" {
				opd:help "The mobilehdr protocol (Mobile Header) is found over the IP layer (IANA protocol number: 135)";
				status obsolete;
			}

			enum "mobilemarket" {
				opd:help "Mobile Market is an online Android and iOS software store developed by China Mobile";
				status obsolete;
			}

			enum "mobilink" {
				opd:help "Mobilink is a proprietary, binary, TCP based protocol which is used to synchronize the contents of multiple mobile client databases with a central SQL Server";
				status obsolete;
			}

			enum "mocean" {
				opd:help "MOcean is an advertising agency";
				status obsolete;
			}

			enum "mocospace" {
				opd:help "MocoSpace is a mobile game community, also known as a mobile social network";
				status obsolete;
			}

			enum "modbus" {
				opd:help "Modbus is a standard communication protocol in industry for connecting industrial electronic devices (SCADA)";
				status obsolete;
			}

			enum "moe_gov" {
				opd:help "Omanian Ministry of Education portal";
				status obsolete;
			}

			enum "mog" {
				opd:help "This classifies the HTTP traffic to the host mog.com";
				status obsolete;
			}

			enum "mogulus" {
				opd:help "Livestream (Mogulus) is a video streaming platform enabling users to broadcast live video";
				status obsolete;
			}

			enum "moi_qatar" {
				opd:help "Ministry of Interior of Qatar";
				status obsolete;
			}

			enum "momoshop" {
				opd:help "Taiwanese online shop";
				status obsolete;
			}

			enum "monex" {
				opd:help "Online broker";
				status obsolete;
			}

			enum "money_163" {
				opd:help "Chinese finance portal";
				status obsolete;
			}

			enum "moneydj" {
				opd:help "Taiwanese finance portal";
				status obsolete;
			}

			enum "monitor" {
				opd:help "Ugandan news portal";
				status obsolete;
			}

			enum "monster" {
				opd:help "Monster.com is an employment website";
				status obsolete;
			}

			enum "moov" {
				opd:help "Malagasy internet web portal";
				status obsolete;
			}

			enum "mop" {
				opd:help "This classifies the HTTP traffic to the host mop.com";
				status obsolete;
			}

			enum "mopub" {
				opd:help "MoPub is a hosted ad serving solution built specifically for mobile publishers";
				status obsolete;
			}

			enum "morefreecamsecrets" {
				opd:help "Adult live webcam site";
				status obsolete;
			}

			enum "mosaiquefm" {
				opd:help "Tunisian radio streaming website";
				status obsolete;
			}

			enum "motika" {
				opd:help "Macedonian video posting website";
				status obsolete;
			}

			enum "motinews" {
				opd:help "News and trending popular website in Mauritius";
				status obsolete;
			}

			enum "mount" {
				opd:help "The Mount protocol is related to the NFS protocol";
				status obsolete;
			}

			enum "mouthshut" {
				opd:help "This classifies the HTTP and SSL traffic to the host mouthshut.com";
				status obsolete;
			}

			enum "mover" {
				opd:help "Uzbek video streaming website";
				status obsolete;
			}

			enum "movie2free" {
				opd:help "Thai movie streaming site and web blog";
				status obsolete;
			}

			enum "movitel" {
				opd:help "Telecom and internet service provider in Mozambique";
				status obsolete;
			}

			enum "mozilla" {
				opd:help "Mozilla is a free-software community";
				status obsolete;
			}

			enum "mozzi" {
				opd:help "International Mobile services provider";
				status obsolete;
			}

			enum "mp3_rocket" {
				opd:help "MP3 Rocket is a music file downloader application";
				status obsolete;
			}

			enum "mp3teca" {
				opd:help "MP3 audio streaming website featuring full albums listening and download";
				status obsolete;
			}

			enum "mpegts" {
				opd:help "MPEG-Transport Stream is a protocol used for MPEG flows transmission";
				status obsolete;
			}

			enum "mpls_in_ip" {
				opd:help "The mpls_in_ip protocol (Multi Protocol Label Switching data-carrying mechanism) is found over the IP layer (IANA protocol number: 137)";
				status obsolete;
			}

			enum "mplus_messenger" {
				opd:help "M+ is a Taiwanese mobile IM application with audio/image file send feature";
				status obsolete;
			}

			enum "mpquest" {
				opd:help "(Deprecated) This classifies the HTTP traffic to the hosts mapquest.com and mapquest.fr";
				status obsolete;
			}

			enum "mq" {
				opd:help "Mq (IBM Websphere MQ) is an inter-application communication protocol";
				status obsolete;
			}

			enum "mqtt" {
				opd:help "MQTT (MQ Telemetry Transport) is a machine-to-machine (M2M)/\"Internet of Things\" connectivity protocol";
				status obsolete;
			}

			enum "ms_communicator" {
				opd:help "Microsoft Office Communicator is a client software launched in October 2007 for conferences which aims to communicate between collaborators using instant messaging, VoIP and videoconference";
				status obsolete;
			}

			enum "ms_onenote" {
				opd:help "Windows program and web application for free-form information gathering, allowing to add text, pictures, audio captures, etc";
				status obsolete;
			}

			enum "ms_planner" {
				opd:help "On-line application of Microsoft Office 365 suite which offers to highly visual way to organize teamwork";
				status obsolete;
			}

			enum "ms_sway" {
				opd:help "On-line application which allows to create and share polished, interactive reports, presentations, personal stories, etc";
				status obsolete;
			}

			enum "ms_translator" {
				opd:help "Microsoft Translator is a cloud-based API that is conveniently integrated into multiple products, tools, and solutions (ex: Bing, Skype, etc)";
				status obsolete;
			}

			enum "msn" {
				opd:help "(Deprecated) The MSN protocol allows the exchange of instant messages";
				status obsolete;
			}

			enum "msn_groups" {
				opd:help "(Deprecated) MSN Groups was a website part of the MSN network which hosted online communities, which contained Web pages, hosted images, and contained a message board";
				status obsolete;
			}

			enum "msn_search" {
				opd:help "(Deprecated) This protocol is used for sending user queries to the MSN Live search engine";
				status obsolete;
			}

			enum "msn_video" {
				opd:help "(Deprecated) This protocol is used by MSN Messenger for video conversations (no longer used since MSN version 8.X)";
				status obsolete;
			}

			enum "msnmobile" {
				opd:help "(Deprecated) MSN Mobile was the MSN instant messenger for mobile";
				status obsolete;
			}

			enum "msrp" {
				opd:help "Message Session Relay Protocol (MSRP) is a protocol for transmitting instant messages, defined by RFC 4975";
				status obsolete;
			}

			enum "msrpc" {
				opd:help "Microsoft Remote Procedure Call (MSRPC) is the Microsoft implementation of the DCE RPC mechanism";
				status obsolete;
			}

			enum "mt" {
				opd:help "This classifies the HTTP traffic to the host mt.co.kr";
				status obsolete;
			}

			enum "mtn" {
				opd:help "Web portal of a South Africa multinational mobile telecommunications company";
				status obsolete;
			}

			enum "mtp" {
				opd:help "The mtp protocol (Multicast Transport Protocol) is found over the IP layer (IANA protocol number: 92)";
				status obsolete;
			}

			enum "mtv" {
				opd:help "This classifies the HTTP traffic to the host mtv.com";
				status obsolete;
			}

			enum "mubi" {
				opd:help "Mubi is a video streaming platform for mobile devices and PC";
				status obsolete;
			}

			enum "mudah" {
				opd:help "Malaisian free classified ads";
				status obsolete;
			}

			enum "muhitelyemen" {
				opd:help "(Deprecated) Yemenite news portal";
				status obsolete;
			}

			enum "multiply" {
				opd:help "This classifies the HTTP traffic to the host multiply.com";
				status obsolete;
			}

			enum "multiupload" {
				opd:help "(Deprecated) This used to classify the HTTP traffic to the multiupload.com service";
				status obsolete;
			}

			enum "musica" {
				opd:help "Musica.com is a site dedicated to songs (lyrics, videos, etc)";
				status obsolete;
			}

			enum "musicchoice" {
				opd:help "MusicChoice (MC) is a media streaming website";
				status obsolete;
			}

			enum "mute" {
				opd:help "Mute is a peer-to-peer protocol";
				status obsolete;
			}

			enum "mux" {
				opd:help "The mux protocol (Multiplexing) is found over the IP layer (IANA protocol number: 18)";
				status obsolete;
			}

			enum "muxlim" {
				opd:help "(Deprecated) This classifies the HTTP traffic to the host muxlim.com";
				status obsolete;
			}

			enum "mxit" {
				opd:help "(Deprecated) MXit was a free instant messaging software application developed by MXit Lifestyle in South Africa";
				status obsolete;
			}

			enum "my_com" {
				opd:help "My.com comprises myMail, MAPS.ME, online and mobile games, targeting service";
				status obsolete;
			}

			enum "my_opera" {
				opd:help "(Deprecated) My Opera (my.opera.com) was a social networking service operated by Opera Software (shut down in March 2014)";
				status obsolete;
			}

			enum "my_talking_tom" {
				opd:help "My Talking Tom is a mobile game";
				status obsolete;
			}

			enum "my_yahoo" {
				opd:help "A customizable web page with news, weather, etc., for Yahoo users";
				status obsolete;
			}

			enum "myanimelist" {
				opd:help "This classifies the HTTP traffic to the host myanimelist.net";
				status obsolete;
			}

			enum "myanmarload" {
				opd:help "Infotainment website in Myanmar";
				status obsolete;
			}

			enum "myauto" {
				opd:help "Georgian classified ads website specialized in motor vehicles";
				status obsolete;
			}

			enum "mychurch" {
				opd:help "This classifies the HTTP and SSL traffic to the host mychurch.org";
				status obsolete;
			}

			enum "mydiv" {
				opd:help "MyDiv is a Russian site for downloading software, games, drivers, scripts";
				status obsolete;
			}

			enum "mydownloader" {
				opd:help "Download files from multiple filesharing websites";
				status obsolete;
			}

			enum "mydrive" {
				opd:help "Free and secure online storage service";
				status obsolete;
			}

			enum "myheritage" {
				opd:help "This classifies the HTTP traffic to the hosts myheritage.fr and myheritage.com";
				status obsolete;
			}

			enum "myjoyonline" {
				opd:help "Ghanaian news portal";
				status obsolete;
			}

			enum "mylife" {
				opd:help "This classifies the HTTP traffic to the host mylife.com";
				status obsolete;
			}

			enum "mymarket" {
				opd:help "Georgian classified ads website";
				status obsolete;
			}

			enum "myoptus" {
				opd:help "Optus (Australian Mobile Operator) application is used to manage mobile accounts on the go";
				status obsolete;
			}

			enum "mypeople_messenger" {
				opd:help "MyPeople Messenger is a cross-platform application providing free text, picture, and video messaging";
				status obsolete;
			}

			enum "mypocket" {
				opd:help "My Pocket is a service that enables the user to send his smartphone data into the personal cloud";
				status obsolete;
			}

			enum "myspace" {
				opd:help "MySpace is a popular social networking site on the Web";
				status obsolete;
			}

			enum "myspace_video" {
				opd:help "This signature detects usage of the video-related features of Myspace";
				status obsolete;
			}

			enum "mysql" {
				opd:help "MySQL is an open source relational database management system (RDBMS) that uses Structured Query Language (SQL), a popular language for adding, accessing, and processing data in a database";
				status obsolete;
			}

			enum "mystart" {
				opd:help "Mystart.com is a web page that provides an internet search engine as well as other services";
				status obsolete;
			}

			enum "myvideo" {
				opd:help "German public video streaming website, featuring musical videos, TV series, movies, etc";
				status obsolete;
			}

			enum "myway" {
				opd:help "Myway.com is a browser hijacker (malware) which changes web browser settings acting like a browser add-on";
				status obsolete;
			}

			enum "mywebsearch" {
				opd:help "This classifies the HTTP traffic to the host mywebsearch.com";
				status obsolete;
			}

			enum "myyearbook" {
				opd:help "(Deprecated) This social networking service is closed";
				status obsolete;
			}

			enum "nabluslive" {
				opd:help "(Deprecated) News portal in Palestinian Territory";
				status obsolete;
			}

			enum "nablustv" {
				opd:help "Popular Palestinian news portal (owned by Paltel)";
				status obsolete;
			}

			enum "nacion" {
				opd:help "Costa Rican news portal";
				status obsolete;
			}

			enum "nagariknews" {
				opd:help "Nepali news portal";
				status obsolete;
			}

			enum "naij" {
				opd:help "Nigerian portal, providing news coverage, music, weather, jokes, job, games and events";
				status obsolete;
			}

			enum "nairaland" {
				opd:help "Nigerian forum hosting site";
				status obsolete;
			}

			enum "namba" {
				opd:help "Kyrgyzstani forum and social networking site";
				status obsolete;
			}

			enum "namibian" {
				opd:help "Daily Namibian newspaper";
				status obsolete;
			}

			enum "namu" {
				opd:help "A popular Korean language wiki website";
				status obsolete;
			}

			enum "napster" {
				opd:help "This classifies the HTTP traffic to the hosts napster.com, napsterinc.tt.omtrdc.net, a1082.b.akamai.net and a1702.b.akamai.net";
				status obsolete;
			}

			enum "narp" {
				opd:help "NBMA Address Resolution Protocol (NARP) allows a source terminal (a host or router), wishing to communicate over a Non-Broadcast Multi-Access (NBMA) link layer network, to find out the NBMA addresses of a destination terminal if the destination terminal is connected to the same NBMA network as the source";
				status obsolete;
			}

			enum "nasa" {
				opd:help "This classifies the HTTP traffic to the host nasa.gov";
				status obsolete;
			}

			enum "nasza_klasa" {
				opd:help "Nasza Klasa is a Polish social networking portal";
				status obsolete;
			}

			enum "nat_pmp" {
				opd:help "The NAT Port Mapping Protocol (NAT-PMP) is a network protocol for establishing network address translation (NAT) settings and port forwarding configurations automatically without user effort";
				status obsolete;
			}

			enum "nate_mail" {
				opd:help "Nate Mail is a South Korea webmail";
				status obsolete;
			}

			enum "natecyworld" {
				opd:help "This classifies the HTTP and SSL traffic to the hosts nate.com";
				status obsolete;
			}

			enum "nation" {
				opd:help "Kenyan news portal";
				status obsolete;
			}

			enum "nationalgeographic" {
				opd:help "Website displaying images and videos of animals, nature and cultures";
				status obsolete;
			}

			enum "nationallottery" {
				opd:help "This classifies the HTTP traffic to the host national-lottery.co.uk";
				status obsolete;
			}

			enum "nationnews" {
				opd:help "Barbadian news portal";
				status obsolete;
			}

			enum "nauta" {
				opd:help "Popular webmail service in Cuba";
				status obsolete;
			}

			enum "naver" {
				opd:help "Naver is a popular Internet content service operator in South Korea";
				status obsolete;
			}

			enum "naver_blog" {
				opd:help "Naver Blog is a South Korean blog hosting website";
				status obsolete;
			}

			enum "naver_mobile" {
				opd:help "Mobile application for Naver (Korean Search Engine)";
				status obsolete;
			}

			enum "naverdrive" {
				opd:help "The file storage client of Naver";
				status obsolete;
			}

			enum "navermail" {
				opd:help "The webmail client of naver.com";
				status obsolete;
			}

			enum "nba" {
				opd:help "News website dedicated to the NBA, featuring video clips";
				status obsolete;
			}

			enum "nba_china" {
				opd:help "Chinese NBA website";
				status obsolete;
			}

			enum "nbc" {
				opd:help "NBC is an American TV network";
				status obsolete;
			}

			enum "nbns" {
				opd:help "NetBios Name Service (NBNS) is a protocol resulting from NetBios, which makes it possible to manage the names in a Microsoft NetBios network";
				status obsolete;
			}

			enum "ncaa" {
				opd:help "The Official website of the NCAA (National Collegiate Athletic Association)";
				status obsolete;
			}

			enum "ncore" {
				opd:help "Famous Hungarian BitTorrent tracker (like bitHUmen)";
				status obsolete;
			}

			enum "ncp" {
				opd:help "The NetWare Core Protocol (NCP) is a network protocol used to access file, print, directory, clock synchronization, messaging, remote command execution and other network service functions";
				status obsolete;
			}

			enum "ndmp" {
				opd:help "NDMP (Network Data Management Protocol) is an open protocol for enterprise-wide network based backup over TCP";
				status obsolete;
			}

			enum "nduoa" {
				opd:help "Chinese Android forum and applications sharing";
				status obsolete;
			}

			enum "nefsis" {
				opd:help "Video conference website";
				status obsolete;
			}

			enum "nefsys" {
				opd:help "(Deprecated) Video conference website";
				status obsolete;
			}

			enum "nend" {
				opd:help "Mobile in-apps ads integration service";
				status obsolete;
			}

			enum "neobux" {
				opd:help "NeoBux excels in providing new business solutions as a Paid-to-Click service";
				status obsolete;
			}

			enum "net" {
				opd:help "Croatian news portal";
				status obsolete;
			}

			enum "net_proxy" {
				opd:help "Net::Proxy is a framework for creating various kinds of network proxies in a very simple way";
				status obsolete;
			}

			enum "netblt" {
				opd:help "The netblt protocol (Bulk Data Transfer Protocol) is found over the IP layer (IANA protocol number: 30)";
				status obsolete;
			}

			enum "netbsd_update" {
				opd:help "NetBSD update manages the updates for NetBSD";
				status obsolete;
			}

			enum "netflix" {
				opd:help "NetFlix is a site using Silverlight protocol to stream videos";
				status obsolete;
			}

			enum "netflow" {
				opd:help "NetFlow is a Cisco protocol that provides nearly real-time traffic monitoring, aggregation and statistic evaluation, multicriteria data flow selection, using source/destination IP addresses, protocols, etc";
				status obsolete;
			}

			enum "neti" {
				opd:help "Estonian web search portal";
				status obsolete;
			}

			enum "netload" {
				opd:help "This classifies the HTTP traffic to the host netload.in";
				status obsolete;
			}

			enum "netlog" {
				opd:help "(Deprecated) Netlog is a social networking website, enabling users to connect to relatives, friends, or unknown people";
				status obsolete;
			}

			enum "netmarble" {
				opd:help "This classifies the HTTP and SSL traffic to the host netmarble.com";
				status obsolete;
			}

			enum "netmeeting_ils" {
				opd:help "Netmeeting ILS is the protocol used between Netmeeting and Internet Locator Servers (ILS)";
				status obsolete;
			}

			enum "netperform" {
				opd:help "Mobile application from Vodafone allowing mobile network performance benchmark and data usage follow-up";
				status obsolete;
			}

			enum "nettby" {
				opd:help "This classifies the HTTP traffic to the host nettby.no";
				status obsolete;
			}

			enum "neulion" {
				opd:help "The NeuLion Digital Platform provides digital video broadcasting, distribution and monetization of live and on-demand content";
				status obsolete;
			}

			enum "new_relic" {
				opd:help "Application performance monitoring and real-time analytics solutions";
				status obsolete;
			}

			enum "news24" {
				opd:help "South African news portal";
				status obsolete;
			}

			enum "news24nepal" {
				opd:help "Infotainment website in Nepal";
				status obsolete;
			}

			enum "news784" {
				opd:help "Leading online news website from St Vincent and the Grenadines";
				status obsolete;
			}

			enum "news_am" {
				opd:help "Armenian news portal";
				status obsolete;
			}

			enum "news_au" {
				opd:help "Australian news portal";
				status obsolete;
			}

			enum "news_mn" {
				opd:help "Mongolian news portal";
				status obsolete;
			}

			enum "newsbook" {
				opd:help "Maltese news portal with national coverage";
				status obsolete;
			}

			enum "newsday" {
				opd:help "National news website from Zimbabwe";
				status obsolete;
			}

			enum "newsit" {
				opd:help "Greek news portal";
				status obsolete;
			}

			enum "newvision" {
				opd:help "Ugandan news portal";
				status obsolete;
			}

			enum "nexian" {
				opd:help "This classifies the HTTP traffic to the hosts nexian.co.id and nexian.us.to";
				status obsolete;
			}

			enum "nexon" {
				opd:help "This classifies the HTTP traffic to the host www.nexon.com";
				status obsolete;
			}

			enum "nexopia" {
				opd:help "This classifies the HTTP and SSL traffic to the host nexopia.com";
				status obsolete;
			}

			enum "nextmedia" {
				opd:help "Media and lifestyle website for Hong Kong and Taiwan";
				status obsolete;
			}

			enum "nfl" {
				opd:help "nfl.com is the NFL website";
				status obsolete;
			}

			enum "nfs" {
				opd:help "The NFS protocol provides transparent remote access to shared file systems across networks as described in RFC 1813";
				status obsolete;
			}

			enum "nfs4" {
				opd:help "The NFS protocol provides transparent remote access to shared file systems across networks as described in RFC 7530 and 7531";
				status obsolete;
			}

			enum "ngo_post" {
				opd:help "This classifies the HTTP and SSL traffic to the host ngopost.org";
				status obsolete;
			}

			enum "ngrok" {
				opd:help "Platform that allows to access a local server from a public URL through reverse proxying";
				status obsolete;
			}

			enum "nhadatso" {
				opd:help "Real estates web portal located in Vietnam";
				status obsolete;
			}

			enum "niconico_douga" {
				opd:help "Nico Nico Douga is a Japanese video streaming platform for mobile devices and PC";
				status obsolete;
			}

			enum "nielsen" {
				opd:help "Nielsen is a global information and measurement company that enables companies to understand consumers and consumer behavior";
				status obsolete;
			}

			enum "nieuwsblad" {
				opd:help "Popular news portal in Belgium";
				status obsolete;
			}

			enum "nifty" {
				opd:help "Japanese web portal and search site";
				status obsolete;
			}

			enum "nigeremploi" {
				opd:help "Job seeking website in Niger";
				status obsolete;
			}

			enum "nike" {
				opd:help "This classifies the HTTP and SSL traffic to the host nike.com";
				status obsolete;
			}

			enum "nikkei" {
				opd:help "Online version of a Japanese newspaper for economists";
				status obsolete;
			}

			enum "nimbuzz_web" {
				opd:help "Instant Messaging client for mobile devices";
				status obsolete;
			}

			enum "ning" {
				opd:help "This classifies the traffic to the host ning.com";
				status obsolete;
			}

			enum "nintendo" {
				opd:help "Japanese multinational video game company";
				status obsolete;
			}

			enum "njuskalo" {
				opd:help "Croatian online classified ads";
				status obsolete;
			}

			enum "nlockmgr" {
				opd:help "The network lock manager is a facility that works in cooperation with the Network File System (NFS) to provide a System V style of advisory file and record locking over the network";
				status obsolete;
			}

			enum "nlsp" {
				opd:help "NetWare Link Services Protocol (NLSP) provides link state routing for Internetwork Packet Exchange networks";
				status obsolete;
			}

			enum "nntp" {
				opd:help "The Network News Transport Protocol (NNTP) is used for the distribution, inquiry, retrieval and posting of net news articles using a reliable stream-based mechanism";
				status obsolete;
			}

			enum "nntps" {
				opd:help "Secure version of the NNTP protocol";
				status obsolete;
			}

			enum "noa" {
				opd:help "Albanian online media portal providing news in Albania, Kosovo, Macedonia, etc";
				status obsolete;
			}

			enum "nod32_update" {
				opd:help "Virus definitions and engine updates for the ESET NOD32 anti-virus";
				status obsolete;
			}

			enum "nokia" {
				opd:help "Nokia is a leader in the fields of network infrastructure, location-based technologies and advanced technologies";
				status obsolete;
			}

			enum "nokia_ovi" {
				opd:help "(Deprecated) Nokia Ovi is a protocol used by customers to synchronize their personal data with their Nokia mobile phone (contacts, mail, calendar, music)";
				status obsolete;
			}

			enum "nonghyup_bank" {
				opd:help "This classifies the HTTP traffic to the host nohyup.com";
				status obsolete;
			}

			enum "nordea" {
				opd:help "Danish online banking and investment web portal";
				status obsolete;
			}

			enum "norton_update" {
				opd:help "Virus definitions and engine updates for the Symantec Norton anti-virus";
				status obsolete;
			}

			enum "noticias24" {
				opd:help "Venezuelan news portal";
				status obsolete;
			}

			enum "novinky" {
				opd:help "Czech news portal";
				status obsolete;
			}

			enum "nownews" {
				opd:help "Taiwanese news portal";
				status obsolete;
			}

			enum "nrdp" {
				opd:help "Nagios Remote Data Processor (NDRP) is a flexible data transport mechanism and processor for Nagios";
				status obsolete;
			}

			enum "nrk" {
				opd:help "Norwegian news portal";
				status obsolete;
			}

			enum "nrl" {
				opd:help "NRL is the National Australian Rugby League website and provides articles and video streaming";
				status obsolete;
			}

			enum "nrpe" {
				opd:help "Nagios Remote Plugin Executor (NRPE) is a Nagios agent that allows remote system monitoring using scripts that are hosted on the remote systems";
				status obsolete;
			}

			enum "nrttv" {
				opd:help "NRT TV is a Kurdish News and current affairs TV channel owned by the Nalia company and is based in Sulaymaniyah, the Capital of Sulaymaniyah";
				status obsolete;
			}

			enum "nsfnet_igp" {
				opd:help "The nsfnet_igp protocol (NSFNET_IGP) is found over the IP layer (IANA protocol number: 85)";
				status obsolete;
			}

			enum "nsh" {
				opd:help "NSH (Network Service Header) is an encapsulation protocol used for service functions chaining";
				status obsolete;
			}

			enum "nspi" {
				opd:help "Name Service Provider Interface is a protocol used by Exchange";
				status obsolete;
			}

			enum "ntd" {
				opd:help "News webportal of a television broadcaster based in New York City";
				status obsolete;
			}

			enum "ntp" {
				opd:help "Network Time Protocol (NTP) is a time synchronization system for computer clocks through the Internet network";
				status obsolete;
			}

			enum "ntv" {
				opd:help "This classifies the HTTP and SSL traffic to the host ntv.co.jp";
				status obsolete;
			}

			enum "ntvbd" {
				opd:help "Bilingual (Bangla and English) infotainment portal covering latest news, entertainment program, sports, tech, etc";
				status obsolete;
			}

			enum "nu" {
				opd:help "Dutch news portal";
				status obsolete;
			}

			enum "nuomi" {
				opd:help "Nuomi.com is a popular group-buying site in China";
				status obsolete;
			}

			enum "nur" {
				opd:help "Kazakhstani news portal";
				status obsolete;
			}

			enum "nust" {
				opd:help "General information website of the Namibia University of Science and Technology";
				status obsolete;
			}

			enum "nvp_ii" {
				opd:help "The nvp_ii protocol (Network Voice Protocol) is found over the IP layer (IANA protocol number: 11)";
				status obsolete;
			}

			enum "nyasatimes" {
				opd:help "Malawi breaking news, business, sports, tourism";
				status obsolete;
			}

			enum "nydailynews" {
				opd:help "This classifies the HTTP traffic to the host nydailynews.com";
				status obsolete;
			}

			enum "nytimes" {
				opd:help "NYTimes.com is the website of The New York Times daily";
				status obsolete;
			}

			enum "nzherald" {
				opd:help "New Zealander news portal";
				status obsolete;
			}

			enum "ocs" {
				opd:help "OCS is a French digital TV package composed of movies/series channels";
				status obsolete;
			}

			enum "ocsp" {
				opd:help "This network protocol is used for validating certificates";
				status obsolete;
			}

			enum "octopz" {
				opd:help "This classifies the HTTP traffic to the host octopz.net";
				status obsolete;
			}

			enum "octoshape" {
				opd:help "Octoshape is a video streaming solution provider for web streaming platforms which uses P2P technology";
				status obsolete;
			}

			enum "odnoklassniki" {
				opd:help "Odnoklassniki is a Russian social network";
				status obsolete;
			}

			enum "odsiebie_najlepsze_net" {
				opd:help "Classifies web browsing on the odsiebie.najlepsze.net Direct DownLoad links service";
				status obsolete;
			}

			enum "office365" {
				opd:help "Office 365 is a Microsoft on-line service, with pay-as-you-go subscription (monthly or annually), giving access to many Microsoft Office applications from the internet, as well as cloud storage, Skype communications, etc";
				status obsolete;
			}

			enum "office_docs" {
				opd:help "Docs.com is a site owned by Microsoft where users can discover, upload and share Office documents";
				status obsolete;
			}

			enum "officedepot" {
				opd:help "This classifies the HTTP and SSL traffic to the hosts officedepot.com, officedepot.fr and officedepot.eu";
				status obsolete;
			}

			enum "offnews" {
				opd:help "Bulgarian news portal";
				status obsolete;
			}

			enum "oicq" {
				opd:help "Oicq is a proprietary messaging protocol developed by Tencent, at the origin of the qq protocol";
				status obsolete;
			}

			enum "okcupid" {
				opd:help "OkCupid is an online dating website";
				status obsolete;
			}

			enum "okezone" {
				opd:help "okezone.com is an Indonesian website";
				status obsolete;
			}

			enum "okta" {
				opd:help "Authentication and identity management cloud services, provided as a SaaS platform";
				status obsolete;
			}

			enum "okwave" {
				opd:help "Decision support for professionals";
				status obsolete;
			}

			enum "olark" {
				opd:help "Olark is a live chat provider";
				status obsolete;
			}

			enum "olx" {
				opd:help "Free international classified ads website";
				status obsolete;
			}

			enum "onclickads" {
				opd:help "Web traffic to Ads Media servers for targeted advertising purposes";
				status obsolete;
			}

			enum "oneclimate" {
				opd:help "(Deprecated) This is deprecated";
				status obsolete;
			}

			enum "onedio" {
				opd:help "Turkish news portal";
				status obsolete;
			}

			enum "onedrive" {
				opd:help "OneDrive (previously SkyDrive, Windows Live SkyDrive, and Windows Live Folders) is a file hosting service";
				status obsolete;
			}

			enum "onef_bf" {
				opd:help "Job seeking website in Burkina Faso";
				status obsolete;
			}

			enum "onehub" {
				opd:help "File sharing website";
				status obsolete;
			}

			enum "onelife" {
				opd:help "OneLife is a service of traveling photo sharing";
				status obsolete;
			}

			enum "onet" {
				opd:help "Polish news portal";
				status obsolete;
			}

			enum "oneworld_org" {
				opd:help "OneWorld is an NGO with a mission to provide internet and mobile phone applications to third-world countries inhabitants";
				status obsolete;
			}

			enum "oneworldtv" {
				opd:help "(Deprecated) This is deprecated";
				status obsolete;
			}

			enum "onlinedown" {
				opd:help "This classifies the HTTP traffic to the host onlinedown.net";
				status obsolete;
			}

			enum "onlinekhabar" {
				opd:help "Nepali news portal";
				status obsolete;
			}

			enum "onliner" {
				opd:help "Belarussian ecommerce website";
				status obsolete;
			}

			enum "onlive" {
				opd:help "Onlive is a platform of cloud gaming";
				status obsolete;
			}

			enum "ontests" {
				opd:help "Guessing game website connected with Facebook, popular in Bolivia";
				status obsolete;
			}

			enum "oovoo" {
				opd:help "oovoo is an instant messenger application, with audio/video support";
				status obsolete;
			}

			enum "ooyala" {
				opd:help "This classifies the HTTP traffic to the hosts l.player.ooyala.com and ooyala.jp";
				status obsolete;
			}

			enum "opcua" {
				opd:help "OPC is the interoperability standard for the secure and reliable exchange of data in the industrial automation space and in other industries";
				status obsolete;
			}

			enum "open_diary" {
				opd:help "This classifies the HTTP and SSL traffic to the host opendiary.com";
				status obsolete;
			}

			enum "openbsd_update" {
				opd:help "This protocol manages OpenBSD updates";
				status obsolete;
			}

			enum "openft" {
				opd:help "OpenFT is a peer-to-peer protocol";
				status obsolete;
			}

			enum "opengw" {
				opd:help "OpenGW (aka VPN Gate) is a Public VPN Relay Servers service, used in several VPN solutions";
				status obsolete;
			}

			enum "openrice" {
				opd:help "OpenRice is an online restaurants guide in Hong Kong";
				status obsolete;
			}

			enum "openrtb" {
				opd:help "OpenRTB is a protocol for the automated trading of digital media across a broad range of platforms, devices, and advertising networks";
				status obsolete;
			}

			enum "opensooq" {
				opd:help "Market place framework aimed to Arab countries";
				status obsolete;
			}

			enum "openstreetmap" {
				opd:help "OpenStreetMap is an open geographical database";
				status obsolete;
			}

			enum "openvpn" {
				opd:help "OpenVPN is an open source software application that implements virtual private network (VPN) techniques for creating secure point-to-point or site-to-site connections in routed or bridged configurations and remote access facilities";
				status obsolete;
			}

			enum "openx" {
				opd:help "OpenX is an advertising company";
				status obsolete;
			}

			enum "opera_mobile_store" {
				opd:help "Opera Mobile Store provides over 300,000 apps and games for more than 7,500 different mobile phone models across Android, Java, Symbian, BlackBerry, Windows Mobile, Windows Phone and iOS platforms";
				status obsolete;
			}

			enum "opera_update" {
				opd:help "Opera Update is the protocol used for the update of the Opera browser";
				status obsolete;
			}

			enum "oppetarkiv" {
				opd:help "Oppet arkiv (Open Archive) is a Swedish television archive website and belongs to the SVT company";
				status obsolete;
			}

			enum "optimizely" {
				opd:help "Optimizely is a firm that makes customer-experience optimization software for companies";
				status obsolete;
			}

			enum "optus" {
				opd:help "Optus is an Australian Mobile Operator, this plugin classifies streams related to Optus website and likely streams generated by other applications or services owned by Optus, such as MyOptus ELP (English Premier League)";
				status obsolete;
			}

			enum "oracle" {
				opd:help "Oracle Corporation is multinational computer technology corporation";
				status obsolete;
			}

			enum "oracle_rac" {
				opd:help "Oracle Real Application Clusters (Oracle RAC) is an option for Oracle Database that provides clustering and high availability";
				status obsolete;
			}

			enum "orange" {
				opd:help "French telecom operator website providing internet and telephone services as well as web and media portal services";
				status obsolete;
			}

			enum "orangemail" {
				opd:help "Orangemail is the webmail of webmail.orange.fr";
				status obsolete;
			}

			enum "orb" {
				opd:help "ORB is a streaming software that enables users to remotely access all their personal digital media files";
				status obsolete;
			}

			enum "orf" {
				opd:help "Austrian news portal";
				status obsolete;
			}

			enum "oriental_daily" {
				opd:help "Oriental Daily news portal includes e-paper versions of the Oriental Daily and Sun Daily newspapers in Hong Kong";
				status obsolete;
			}

			enum "origjinale" {
				opd:help "Albanian news portal";
				status obsolete;
			}

			enum "origo" {
				opd:help "Hungarian news portal";
				status obsolete;
			}

			enum "orkut" {
				opd:help "Orkut is a social networking website competing with Facebook or Twitter, popular in Brazil and now owned and operated by Google Inc";
				status obsolete;
			}

			enum "osinl" {
				opd:help "ISO Network Layer Protocol is used by Cisco Equipment to transmit OSI protocols (IS-IS, etc) over Ethernet";
				status obsolete;
			}

			enum "ospf" {
				opd:help "OSPF (Open Short Path First) is a link state routing protocol used within large autonomous system networks";
				status obsolete;
			}

			enum "ouedkniss" {
				opd:help "Algerian internet portal";
				status obsolete;
			}

			enum "outbrain" {
				opd:help "Outbrain is a content discovery platform whose content marketing module offers to help Internet publishers";
				status obsolete;
			}

			enum "outeverywhere" {
				opd:help "This classifies the HTTP traffic to the host outeverywhere.com";
				status obsolete;
			}

			enum "outlook" {
				opd:help "On-line Microsoft Outlook encrypted service, also included in the Office 365 productivity suite";
				status obsolete;
			}

			enum "ovaciondigital" {
				opd:help "Uruguayan sports and multimedia website";
				status obsolete;
			}

			enum "over_blog" {
				opd:help "French and American blog administration website";
				status obsolete;
			}

			enum "owa" {
				opd:help "Outlook Web App is used to access e-mail (including support for S/MIME), calendars, contacts, tasks, documents (used with SharePoint or in 2010 Office Web Apps), and other mailbox content when access to the Microsoft Outlook desktop application is unavailable";
				status obsolete;
			}

			enum "ows" {
				opd:help "Software editor of secured messaging applications";
				status obsolete;
			}

			enum "oxu" {
				opd:help "Azerbaijani news portal";
				status obsolete;
			}

			enum "padabum" {
				opd:help "Padabum is a Russian e-books download website";
				status obsolete;
			}

			enum "paipai" {
				opd:help "This classifies the HTTP traffic to the host paipai.com";
				status obsolete;
			}

			enum "paltalk" {
				opd:help "Paltalk is an instant messaging protocol";
				status obsolete;
			}

			enum "paltalk_audio" {
				opd:help "Proprietary protocol used by Paltalk in audio chats";
				status obsolete;
			}

			enum "paltalk_transfer" {
				opd:help "Paltalk is an instant messaging protocol";
				status obsolete;
			}

			enum "paltalk_video" {
				opd:help "Proprietary protocol used by Paltalk in video";
				status obsolete;
			}

			enum "palweather" {
				opd:help "Palestinian meteorological portal";
				status obsolete;
			}

			enum "panda_update" {
				opd:help "Panda_update is the protocol used for panda software updates";
				status obsolete;
			}

			enum "pando" {
				opd:help "(Deprecated) pando is a peer-to-peer protocol";
				status obsolete;
			}

			enum "pandora" {
				opd:help "Pandora is a customizable music streaming service popular in the United States";
				status obsolete;
			}

			enum "pandora_tv" {
				opd:help "This classifies the HTTP traffic to the host pandora.tv";
				status obsolete;
			}

			enum "panet" {
				opd:help "News and entertainment web portal";
				status obsolete;
			}

			enum "panoramio" {
				opd:help "Panoramio is a geolocalized photo-sharing website";
				status obsolete;
			}

			enum "pantip" {
				opd:help "Thai information and entertainment portal";
				status obsolete;
			}

			enum "pap" {
				opd:help "The Password Authentication Protocol (PAP) provides a simple authentication method over a PPP link";
				status obsolete;
			}

			enum "paraguay" {
				opd:help "Paraguayan news portal";
				status obsolete;
			}

			enum "paran" {
				opd:help "(Deprecated) This classifies the HTTP traffic to the host praran.com";
				status obsolete;
			}

			enum "parse" {
				opd:help "Parse is a Mobile Backend platform working as a Service provider";
				status obsolete;
			}

			enum "partis" {
				opd:help "Slovenian news portal";
				status obsolete;
			}

			enum "partnerup" {
				opd:help "This classifies the HTTP traffic to the host partnerup.com";
				status obsolete;
			}

			enum "party_poker" {
				opd:help "Online poker gaming website";
				status obsolete;
			}

			enum "passportstamp" {
				opd:help "This classifies the HTTP traffic to the host passportstamp.com";
				status obsolete;
			}

			enum "pastebin" {
				opd:help "A pastebin is a type of web application where anyone can store plain text";
				status obsolete;
			}

			enum "pastebin_posting" {
				opd:help "Pastebin_posting is used to classify posting workflow of the pastebin.com website";
				status obsolete;
			}

			enum "path" {
				opd:help "It is a free social instant messenger for private messaging and sharing photos, videos, music, etc";
				status obsolete;
			}

			enum "payeasy" {
				opd:help "Taiwanese online beauty store";
				status obsolete;
			}

			enum "paypal" {
				opd:help "Online payment services";
				status obsolete;
			}

			enum "pazar3" {
				opd:help "Macedonian classified ads";
				status obsolete;
			}

			enum "pbx" {
				opd:help "Symantex Private Branch Exchange service protocol, used in the Veritas NetBackup data backup software";
				status obsolete;
			}

			enum "pcanywhere" {
				opd:help "PCAnywhere is a remote control solution";
				status obsolete;
			}

			enum "pcgames" {
				opd:help "Chinese Games portal";
				status obsolete;
			}

			enum "pchome" {
				opd:help "Taiwanese Web portal (news, webmail, shopping, etc)";
				status obsolete;
			}

			enum "pclady" {
				opd:help "Chinese beauty and fashion portal";
				status obsolete;
			}

			enum "pcloud" {
				opd:help "Personal and business online storage web service";
				status obsolete;
			}

			enum "pconline" {
				opd:help "This classifies the HTTP traffic to the host pconline.com.cn";
				status obsolete;
			}

			enum "pd_proxy" {
				opd:help "Tunneling software that can secure your internet connection by encrypting all your connections to the internet";
				status obsolete;
			}

			enum "peacefmonline" {
				opd:help "Hungarian news portal";
				status obsolete;
			}

			enum "peercast" {
				opd:help "PeerCast is an open-source multimedia streaming protocol";
				status obsolete;
			}

			enum "peerguardian" {
				opd:help "PeerGuardian is capable of blocking incoming and outgoing connections based on IP blacklists";
				status obsolete;
			}

			enum "pengyou" {
				opd:help "This classifies the HTTP traffic to the host pengyou.com";
				status obsolete;
			}

			enum "people" {
				opd:help "This classifies the HTTP traffic to the host people.com.cn";
				status obsolete;
			}

			enum "perfect_dark" {
				opd:help "Perfect Dark is a peer-to-peer file-sharing (P2P) protocol from Japan";
				status obsolete;
			}

			enum "perforce" {
				opd:help "Perforce is a commercial, proprietary, centralized revision control system developed by Perforce Software, Inc";
				status obsolete;
			}

			enum "perform" {
				opd:help "Perform is a digital sports content delivery network and media group";
				status obsolete;
			}

			enum "perfspot" {
				opd:help "Perfspot is a social networking website, enabling users to connect to relatives, friends, or unknown people and to share files";
				status obsolete;
			}

			enum "periscope" {
				opd:help "Periscope is a live video streaming application";
				status obsolete;
			}

			enum "persianblog" {
				opd:help "Persian blogging platform";
				status obsolete;
			}

			enum "petitesannonces" {
				opd:help "French Polynesian online classified ads";
				status obsolete;
			}

			enum "peyvandha" {
				opd:help "Persian internet portal";
				status obsolete;
			}

			enum "pgm" {
				opd:help "The pgm protocol (PGM Reliable Transport Protocol) is found over the IP layer (IANA protocol number: 113)";
				status obsolete;
			}

			enum "philenews" {
				opd:help "Cypriot news portal";
				status obsolete;
			}

			enum "photobucket" {
				opd:help "Photo sharing web-service, with advanced editing features, available for desktop and mobile devices";
				status obsolete;
			}

			enum "phproxy" {
				opd:help "PHProxy is a web HTTP proxy programmed in PHP meant to bypass firewalls and access otherwise inaccessible resources";
				status obsolete;
			}

			enum "phweet" {
				opd:help "This classifies the HTTP traffic to the host phweet.com";
				status obsolete;
			}

			enum "pi_af" {
				opd:help "OSI PI Analysis Framework SCADA protocol (AF Server, MDB Sync, etc.)";
				status obsolete;
			}

			enum "pi_data" {
				opd:help "OSI PI DataArchive and Server SCADA protocol (ProcessBook, Datalink, etc.)";
				status obsolete;
			}

			enum "pichat" {
				opd:help "Online Chat Application ( pichat.net )";
				status obsolete;
			}

			enum "pik" {
				opd:help "Bosnian online trading website";
				status obsolete;
			}

			enum "pim" {
				opd:help "The PIM Protocol provides an efficient routing of multicast groups that may span wide-area Internet zones";
				status obsolete;
			}

			enum "pimang" {
				opd:help "This classifies the HTTP traffic to the hosts pimang.com and www.pmang.com";
				status obsolete;
			}

			enum "pingsta" {
				opd:help "This classifies the HTTP traffic to the host pingsta.com";
				status obsolete;
			}

			enum "pinterest" {
				opd:help "On-line service that allows users to attach personal elements on some kind of pinboard";
				status obsolete;
			}

			enum "piolet" {
				opd:help "P2P for music files";
				status obsolete;
			}

			enum "pipe" {
				opd:help "The pipe protocol (Private IP Encapsulation within IP) is found over the IP layer (IANA protocol number: 131)";
				status obsolete;
			}

			enum "pixiv" {
				opd:help "Website dedicated to Japanese fanarts and drawings";
				status obsolete;
			}

			enum "pixnet" {
				opd:help "Taiwanese web albums and blog service";
				status obsolete;
			}

			enum "plants_vs_zombies" {
				opd:help "Plants vs Zombie is a mobile game";
				status obsolete;
			}

			enum "plaxo" {
				opd:help "This classifies the HTTP traffic to the host plaxo.com";
				status obsolete;
			}

			enum "playahead" {
				opd:help "(Deprecated) This classifies the HTTP traffic to the host playahead.se";
				status obsolete;
			}

			enum "playstation" {
				opd:help "This classifies the HTTP traffic to the host playstation.com";
				status obsolete;
			}

			enum "plentyoffish" {
				opd:help "Free online dating site, popular primarily in Canada, the UK, Australia, and the United States";
				status obsolete;
			}

			enum "plius" {
				opd:help "Lithuanian online classified ads";
				status obsolete;
			}

			enum "plurk" {
				opd:help "Plurk is a social network popular in Taiwan";
				status obsolete;
			}

			enum "pmhotnews" {
				opd:help "The Popular Magazine is a web portal featuring entertainment news in Cambodia";
				status obsolete;
			}

			enum "pnni" {
				opd:help "The pnni protocol (PNNI over IP) is found over the IP layer (IANA protocol number: 102)";
				status obsolete;
			}

			enum "poco" {
				opd:help "Poco is a Chinese webportal, which allow users to share pictures, chat, exchange files, etc";
				status obsolete;
			}

			enum "pogo" {
				opd:help "Pogo.com is a free online casual gaming website";
				status obsolete;
			}

			enum "point" {
				opd:help "Moldovian news portal";
				status obsolete;
			}

			enum "pokemon_go" {
				opd:help "Pokemon GO is an online mobile game by Niantic Labs";
				status obsolete;
			}

			enum "poker_stars" {
				opd:help "Poker Stars is an online poker cardroom";
				status obsolete;
			}

			enum "pole_emploi" {
				opd:help "French website for job seekers";
				status obsolete;
			}

			enum "politis_news" {
				opd:help "Daily morning Cypriot newspaper on the web with national and local coverage";
				status obsolete;
			}

			enum "pop3" {
				opd:help "Post Office Protocol - Version 3 (POP3) allows a workstation to simply and dynamically access a mail stored on a mail server";
				status obsolete;
			}

			enum "pop3s" {
				opd:help "Secure version of the POP3 protocol";
				status obsolete;
			}

			enum "popads" {
				opd:help "Online advertising solutions provider";
				status obsolete;
			}

			enum "porn555" {
				opd:help "Popular adult videos website";
				status obsolete;
			}

			enum "pornhub" {
				opd:help "Pornhub is a popular adult video streaming website";
				status obsolete;
			}

			enum "pornsurvey" {
				opd:help "The Porn Survey promotes various Adult offers";
				status obsolete;
			}

			enum "portalanalitika" {
				opd:help "Generic news portal in Montenegro";
				status obsolete;
			}

			enum "portmap" {
				opd:help "Port Mapper protocol maps RPC program and version numbers to port numbers";
				status obsolete;
			}

			enum "postgres" {
				opd:help "PostgreSQL is a sophisticated Object-Relational DBMS, supporting almost all SQL constructs, including subselects, transactions, and user-defined types and functions";
				status obsolete;
			}

			enum "postimees" {
				opd:help "Estonian news portal";
				status obsolete;
			}

			enum "pou" {
				opd:help "Mobile game";
				status obsolete;
			}

			enum "power_bi" {
				opd:help "On-line Microsoft Business Intelligence application, also included in the Office 365 productivity suite";
				status obsolete;
			}

			enum "powerpoint_online" {
				opd:help "On-line version of Microsoft Powerpoint";
				status obsolete;
			}

			enum "ppfilm" {
				opd:help "PP Film (aka PIPI.cn or PIPI Player) is a Chinese peer-to-peer and VOD service";
				status obsolete;
			}

			enum "pplive" {
				opd:help "PPLIVE is an application intended to watch TV in peer-to-peer";
				status obsolete;
			}

			enum "ppomppu" {
				opd:help "Southern Korean forum on hightech, food, society and lifestyle";
				status obsolete;
			}

			enum "pps" {
				opd:help "(Deprecated) This classifies the HTTP traffic to the host pps.tv";
				status obsolete;
			}

			enum "ppstream" {
				opd:help "The PPStream protocol provides audio and video streaming";
				status obsolete;
			}

			enum "pptp" {
				opd:help "Point-to-Point Tunneling Protocol allows the Point to Point Protocol (PPP) to be tunneled through an IP network";
				status obsolete;
			}

			enum "pptv" {
				opd:help "This classifies the HTTP and SSL traffic to the host pptv.com";
				status obsolete;
			}

			enum "prensa" {
				opd:help "Panamanian news portal";
				status obsolete;
			}

			enum "prensalibre" {
				opd:help "Guatemalan news portal";
				status obsolete;
			}

			enum "present" {
				opd:help "(Deprecated) This web service is closed";
				status obsolete;
			}

			enum "press24" {
				opd:help "Macedonian news portal";
				status obsolete;
			}

			enum "pressan" {
				opd:help "Icelandic news portal";
				status obsolete;
			}

			enum "priceminister" {
				opd:help "This classifies the traffic to the host priceminister.com";
				status obsolete;
			}

			enum "pricerunner" {
				opd:help "Pricerunner is a price comparison service";
				status obsolete;
			}

			enum "primewire" {
				opd:help "Video streaming website";
				status obsolete;
			}

			enum "print_io" {
				opd:help "Print.io is a commerce tools for everything from personalized products to business printing and branded merchandise";
				status obsolete;
			}

			enum "private_enc" {
				opd:help "The private_enc protocol (Any private encryption scheme) is found over the IP layer (IANA protocol number: 99)";
				status obsolete;
			}

			enum "privax" {
				opd:help "This classifies the HTTP traffic to the host privax.us";
				status obsolete;
			}

			enum "prm" {
				opd:help "The prm protocol (Packet Radio Measurement) is found over the IP layer (IANA protocol number: 21)";
				status obsolete;
			}

			enum "prodavalnik" {
				opd:help "(Deprecated) Bulgarian classified ads";
				status obsolete;
			}

			enum "profinet" {
				opd:help "PROFINET (an acronym for Process Field Net) is an industry technical standard for data communication over Industrial Ethernet, designed for controlling and collecting data from equipment in industrial systems, with a particular strength in delivering data under tight time constraints (1ms or less)";
				status obsolete;
			}

			enum "pronto" {
				opd:help "Pronto is the XIMSS protocol used by CommuniGate Pro";
				status obsolete;
			}

			enum "propertyguru" {
				opd:help "Singaporean property sale and rental searching website";
				status obsolete;
			}

			enum "prothom_alo" {
				opd:help "Bangladeshi newspaper online portal";
				status obsolete;
			}

			enum "protothema" {
				opd:help "Greek news portal";
				status obsolete;
			}

			enum "proxeasy" {
				opd:help "This classifies the HTTP traffic to the host proxeasy.com";
				status obsolete;
			}

			enum "proxono" {
				opd:help "This classifies the HTTP traffic to the hosts proxono.org and proxono.info";
				status obsolete;
			}

			enum "psiphon" {
				opd:help "Internet proxy/redirector which allows uncensored access to web content";
				status obsolete;
			}

			enum "psn" {
				opd:help "PlayStation Network (PSN) is the on-line gaming service for consoles made by Sony";
				status obsolete;
			}

			enum "psyonix" {
				opd:help "Psyonix is a game editor";
				status obsolete;
			}

			enum "ptp" {
				opd:help "The ptp protocol (Performance Transparency Protocol) is found over the IP layer (IANA protocol number: 123)";
				status obsolete;
			}

			enum "public" {
				opd:help "(Deprecated) Website providing communications from the Government of Luxembourg";
				status obsolete;
			}

			enum "public_lu" {
				opd:help "Website providing communications from the Government of Luxembourg";
				status obsolete;
			}

			enum "publinews" {
				opd:help "News website in Guatemala";
				status obsolete;
			}

			enum "pubmatic" {
				opd:help "PubMatic is an advertising company";
				status obsolete;
			}

			enum "puls24" {
				opd:help "Macedonian news portal";
				status obsolete;
			}

			enum "pulse_com_gh" {
				opd:help "Ghanean news portal";
				status obsolete;
			}

			enum "pulsepoint" {
				opd:help "PulsePoint is a programmatic advertising technology company";
				status obsolete;
			}

			enum "punyumunyu" {
				opd:help "Japanese adult movie website";
				status obsolete;
			}

			enum "pup" {
				opd:help "The pup protocol (PUP) is found over the IP layer (IANA protocol number: 12)";
				status obsolete;
			}

			enum "putlocker" {
				opd:help "Site for watching free online movies";
				status obsolete;
			}

			enum "puzzle_and_dragon" {
				opd:help "Japanese Mobile game";
				status obsolete;
			}

			enum "pvp" {
				opd:help "The pvp protocol (Packet Video Protocol) is found over the IP layer (IANA protocol number: 75)";
				status obsolete;
			}

			enum "q931" {
				opd:help "The Q.931 protocol enables the use of voice and image on networks for video conferencing";
				status obsolete;
			}

			enum "qapacity" {
				opd:help "(Deprecated) This classifies the HTTP traffic to the host qapacity.com";
				status obsolete;
			}

			enum "qatarairways" {
				opd:help "Qatar Airways is the state-owned airline company of Qatar";
				status obsolete;
			}

			enum "qatarliving" {
				opd:help "Qatari online classified ads";
				status obsolete;
			}

			enum "qik_video" {
				opd:help "QIK is a PC/smartphone application allowing live and VOD streaming from the web";
				status obsolete;
			}

			enum "qiniu" {
				opd:help "Shanghai Qiniu Information Technologies Co., Ltd";
				status obsolete;
			}

			enum "qnx" {
				opd:help "The qnx protocol (QNX) is found over the IP layer (IANA protocol number: 106)";
				status obsolete;
			}

			enum "qoo10" {
				opd:help "Singaporean online fashion and trend shopping market";
				status obsolete;
			}

			enum "qq" {
				opd:help "QQ is a popular free instant messaging computer program in China";
				status obsolete;
			}

			enum "qq_blog" {
				opd:help "Tencent blog hosting service";
				status obsolete;
			}

			enum "qq_dancer" {
				opd:help "QQ dancer is an online multiplayer dancing and music game from Tencent";
				status obsolete;
			}

			enum "qq_finance" {
				opd:help "Tencent finance news portal";
				status obsolete;
			}

			enum "qq_games" {
				opd:help "Game applications and web portal for tencent games";
				status obsolete;
			}

			enum "qq_lady" {
				opd:help "Tencent fashion website";
				status obsolete;
			}

			enum "qq_mail" {
				opd:help "Tencent Webmail";
				status obsolete;
			}

			enum "qq_news" {
				opd:help "Chinese news portal";
				status obsolete;
			}

			enum "qq_r2" {
				opd:help "QQ R2 is an online multiplayer game from Tencent";
				status obsolete;
			}

			enum "qq_speed" {
				opd:help "QQ speed is an online multiplayer dancing and music game from Tencent";
				status obsolete;
			}

			enum "qq_transfer" {
				opd:help "(Deprecated) File transfer over QQ";
				status obsolete;
			}

			enum "qq_web" {
				opd:help "QQ.com is a multi-service Chinese web portal hosted by Tencent";
				status obsolete;
			}

			enum "qq_weibo" {
				opd:help "QQ WeiBo is a Chinese Twitter-like micro-blogging website";
				status obsolete;
			}

			enum "qqdownload" {
				opd:help "QQDownload is a Chinese download manager";
				status obsolete;
			}

			enum "qqlive" {
				opd:help "QQLive is an application intended to watch TV in Peer-to-Peer mode";
				status obsolete;
			}

			enum "qqmusic" {
				opd:help "QQMusic is a Chinese peer-to-peer file sharing software";
				status obsolete;
			}

			enum "qqstream" {
				opd:help "QQStream is a Chinese peer-to-peer file sharing software";
				status obsolete;
			}

			enum "qqvideo" {
				opd:help "QQVideo is the QQ video service platform";
				status obsolete;
			}

			enum "qtrax" {
				opd:help "BitTorrent tracker search engine";
				status obsolete;
			}

			enum "quake" {
				opd:help "Quake is a protocol allowing communication between Quake Clients and Quake servers";
				status obsolete;
			}

			enum "quantcast" {
				opd:help "Quantcast provides audience and advertisement services for websites";
				status obsolete;
			}

			enum "quantum_dxi_ost" {
				opd:help "Classifies the Symantec NetBackup streams that use the Quantum DXi replication solution";
				status obsolete;
			}

			enum "quarterlife" {
				opd:help "This classifies the HTTP traffic to the host quarterlife.com";
				status obsolete;
			}

			enum "quic" {
				opd:help "QUIC is an open networking protocol developed primarily at Google for transporting web content";
				status obsolete;
			}

			enum "quickflix" {
				opd:help "Australian website with movies and TV shows video streaming";
				status obsolete;
			}

			enum "quizup" {
				opd:help "Mobile game";
				status obsolete;
			}

			enum "qunar" {
				opd:help "Chinese travel website";
				status obsolete;
			}

			enum "qvod" {
				opd:help "QVOD is a peer-to-peer based Video-On-Demand player";
				status obsolete;
			}

			enum "qzone" {
				opd:help "Tencent social network";
				status obsolete;
			}

			enum "r10" {
				opd:help "Turkish forum on multiple subjects";
				status obsolete;
			}

			enum "rackspace" {
				opd:help "Rackspace Inc. is a managed cloud computing company";
				status obsolete;
			}

			enum "radiko" {
				opd:help "Radio broadcast web retransmission service";
				status obsolete;
			}

			enum "radio1" {
				opd:help "French Polynesian radio broadcast website";
				status obsolete;
			}

			enum "radio_bethlehem_2000" {
				opd:help "Palestinian local radio website, featuring live streaming";
				status obsolete;
			}

			enum "radiookapi" {
				opd:help "News website founded by the United Nations Mission in the Democratic Republic of Congo (MONUC) and the Swiss NGO Foundation Hirondelle";
				status obsolete;
			}

			enum "radiumone" {
				opd:help "RadiumOne is an advertising platform which covers online, video, social and mobile advertising";
				status obsolete;
			}

			enum "radius" {
				opd:help "RADIUS (Remote Authentication Dial-In User Service) is a client/server protocol that enables remote access servers to communicate with a central server to authenticate dial-in users and authorize their access to the requested system or service";
				status obsolete;
			}

			enum "radiusim" {
				opd:help "This classifies the HTTP traffic to the host radiusim.com";
				status obsolete;
			}

			enum "radmin" {
				opd:help "Radmin is a control software which is able to establish a remote secure connection between computers";
				status obsolete;
			}

			enum "rainbow" {
				opd:help "Rainbow is an Instant Messaging and VoIP application by Alcatel-Lucent Enterprise";
				status obsolete;
			}

			enum "rakuten" {
				opd:help "Online market place for selling goods and auctions";
				status obsolete;
			}

			enum "ramallah" {
				opd:help "Palestinian Ramallah City related news portal";
				status obsolete;
			}

			enum "rambler" {
				opd:help "Rambler is a Russian information internet portal";
				status obsolete;
			}

			enum "rambler_webmail" {
				opd:help "Rambler webmail is the webmail of the Russian website rambler.ru";
				status obsolete;
			}

			enum "ranap" {
				opd:help "RANAP (Radio Access Network Application Part) is used in RAN (Radio Access Network)";
				status obsolete;
			}

			enum "rapidshare" {
				opd:help "RapidShare is an online solution to store, send and share files";
				status obsolete;
			}

			enum "rapidupload_com" {
				opd:help "(Deprecated) Classifies web browsing on the rapidupload.com Direct DownLoad links service";
				status obsolete;
			}

			enum "rappler" {
				opd:help "Rappler is a social news network";
				status obsolete;
			}

			enum "ratopati" {
				opd:help "Politics, National and international issues, sports, entertainment and other news from Nepal";
				status obsolete;
			}

			enum "raulken" {
				opd:help "BitTorrent tracker search engine";
				status obsolete;
			}

			enum "ravelry" {
				opd:help "This classifies the HTTP traffic to the host www.ravelry.com";
				status obsolete;
			}

			enum "raya" {
				opd:help "Palestinian news portal";
				status obsolete;
			}

			enum "rayfile" {
				opd:help "BitTorrent tracker search engine";
				status obsolete;
			}

			enum "rcsc" {
				opd:help "Web portal of the Royal Government of Bhutan";
				status obsolete;
			}

			enum "rdp" {
				opd:help "A key component of Terminal Server is the Remote Desktop Protocol which allows a thin client to communicate with the Terminal Server over the network";
				status obsolete;
			}

			enum "rdt" {
				opd:help "This protocol is used to transport audio/video data";
				status obsolete;
			}

			enum "realestate" {
				opd:help "Australian site for property solutions";
				status obsolete;
			}

			enum "realtor" {
				opd:help "This classifies the HTTP and SSL traffic to the host realtor.com";
				status obsolete;
			}

			enum "reddit" {
				opd:help "Social news website";
				status obsolete;
			}

			enum "redhat_update" {
				opd:help "This protocol is used for Red Hat updates";
				status obsolete;
			}

			enum "redtube" {
				opd:help "Redtube is a popular adult video streaming website";
				status obsolete;
			}

			enum "reflected_networks" {
				opd:help "Reflected Networks is a managed hosting and custom hosting solutions";
				status obsolete;
			}

			enum "reklama5" {
				opd:help "Macedonian classified ads";
				status obsolete;
			}

			enum "renren" {
				opd:help "This classifies the HTTP and SSL traffic to the host renren.com";
				status obsolete;
			}

			enum "repubblica" {
				opd:help "Italian news portal";
				status obsolete;
			}

			enum "republika" {
				opd:help "This classifies the HTTP and SSL traffic to the host republika.co.id";
				status obsolete;
			}

			enum "republika_slovenija" {
				opd:help "Web portal of the Slovenian government";
				status obsolete;
			}

			enum "researchgate" {
				opd:help "This classifies the HTTP traffic to the host researchgate.net";
				status obsolete;
			}

			enum "retroshare" {
				opd:help "Retroshare is a communication and file-sharing Open Source platform which is secured and decentralized";
				status obsolete;
			}

			enum "reuters" {
				opd:help "This classifies the HTTP and SSL traffic to the host reuters.com";
				status obsolete;
			}

			enum "revcontent" {
				opd:help "Revcontent is a content recommendation platform";
				status obsolete;
			}

			enum "reverbnation" {
				opd:help "This classifies the HTTP traffic to the host reverbnation.com";
				status obsolete;
			}

			enum "reverso" {
				opd:help "This classifies the HTTP traffic to the host reverso.net";
				status obsolete;
			}

			enum "revolico" {
				opd:help "Popular classified ads website in Cuba";
				status obsolete;
			}

			enum "rfb" {
				opd:help "RFB (Remote Frame Buffer) is a simple protocol for remote access to graphical user interfaces";
				status obsolete;
			}

			enum "rhapsody" {
				opd:help "Rhapsody is a subscription based music streaming service";
				status obsolete;
			}

			enum "ricardo" {
				opd:help "Swiss online trading website";
				status obsolete;
			}

			enum "riffsy" {
				opd:help "Riffsy's GIF Keyboard (Tenor.co) permits users to share and discover animated GIFs and videos on mobile";
				status obsolete;
			}

			enum "rimnow" {
				opd:help "Mauritanian news portal";
				status obsolete;
			}

			enum "ringring" {
				opd:help "Vietnamese news portal";
				status obsolete;
			}

			enum "rip1" {
				opd:help "RIP1 (Routing Information Protocol Version 1) is a Distance Vector routing protocol used in Inter Autonomous Systems";
				status obsolete;
			}

			enum "rip2" {
				opd:help "RIP2 (Routing Information Protocol Version 2) is an enhancement of the Version 1 of the protocol";
				status obsolete;
			}

			enum "ripng1" {
				opd:help "RIPng (RIP New Generation) is intended to allow routers to exchange information for computing routes through an IPv6-based network";
				status obsolete;
			}

			enum "rlcdn" {
				opd:help "Rlcdn appends social network data to customer database to help discovering where customers are across the social web";
				status obsolete;
			}

			enum "rlogin" {
				opd:help "The Rlogin protocol is used to establish a bidirectional communication to distant terminals";
				status obsolete;
			}

			enum "rlp" {
				opd:help "Resource Location Protocol (RLP) is a protocol used to discover the location of resources present in a network";
				status obsolete;
			}

			enum "rmi_iiop" {
				opd:help "RMI-IIOP (Remote Method Invocation over Internet Inter-ORB Protocol) delivers CORBA distributed architecture to Java 2 platform, using both remote method invocation system RMI and IIOP protocol";
				status obsolete;
			}

			enum "rmix" {
				opd:help "Ramallah Mix is a generic news and entertainment portal in Palestinian Territory";
				status obsolete;
			}

			enum "rmvbusters" {
				opd:help "BitTorrent tracker search engine";
				status obsolete;
			}

			enum "roboform" {
				opd:help "Roboform is a password management and web form filling program";
				status obsolete;
			}

			enum "rocket_league" {
				opd:help "Rocket League is a game made by Psyonix";
				status obsolete;
			}

			enum "rogers" {
				opd:help "Rogers TV is a group of community channels owned by Rogers Communications";
				status obsolete;
			}

			enum "rohc" {
				opd:help "The rohc protocol (Robust Header Compression) is found over the IP layer (IANA protocol number: 142)";
				status obsolete;
			}

			enum "rolloid" {
				opd:help "Infotainment website in Andorra";
				status obsolete;
			}

			enum "rollout" {
				opd:help "With Rollout.io, mobile developers can quickly react to quality issues in production by hot-patching bugs in real time";
				status obsolete;
			}

			enum "rovi" {
				opd:help "Rovi Corporation is a company based in the United States whose patents, products, and technologies include copy protection, software licensing and \"search recommendation\" on devices such as set-top boxes, digital video recorders, TVs, and mobile and tablet devices";
				status obsolete;
			}

			enum "rovio" {
				opd:help "Rovio is a mobile game editor";
				status obsolete;
			}

			enum "royalgazette" {
				opd:help "Bermudian newspaper web portal";
				status obsolete;
			}

			enum "royanews" {
				opd:help "Jordanian news portal";
				status obsolete;
			}

			enum "rozetka" {
				opd:help "Online shopping website from Ukraine";
				status obsolete;
			}

			enum "rpc" {
				opd:help "RPC (Remote Procedure Call) is an easy and popular paradigm for implementing the client-server model of distributed computing";
				status obsolete;
			}

			enum "rpl" {
				opd:help "IBM Remote Program Load allows a client computer to retrieve startup and configuration software from a server when it starts";
				status obsolete;
			}

			enum "rquota" {
				opd:help "The RQuota protocol enables the implementation of quotas on remote machines";
				status obsolete;
			}

			enum "rsh" {
				opd:help "The RSH protocol allows a user to establish a secure connection to a remote host and to obtain a shell allowing commands to be sent to the remote machine to be executed";
				status obsolete;
			}

			enum "rss" {
				opd:help "RSS is a family of web feed formats used to publish frequently updated works in a standardized format";
				status obsolete;
			}

			enum "rstat" {
				opd:help "The RStat protocol is used in the Sun NFS family to exchange statistics on network activity";
				status obsolete;
			}

			enum "rsvp" {
				opd:help "RSVP is a Resource reSerVation setup Protocol designed for an integrated services Internet";
				status obsolete;
			}

			enum "rsvp_e2e_ignore" {
				opd:help "The rsvp_e2e_ignore protocol (Original experimental academic or proprietary protocols) is found over the IP layer (IANA protocol number: 134)";
				status obsolete;
			}

			enum "rsync" {
				opd:help "Rsync is a protocol used by various services performing updates";
				status obsolete;
			}

			enum "rt" {
				opd:help "Worldwide Russian news channel in Russian, Arabic, Spanish and English";
				status obsolete;
			}

			enum "rtcp" {
				opd:help "The Real-time Transport Control Protocol (RTCP) allows monitoring of the data delivery in a manner scalable to large multicast networks, and to provide minimal control and identification functionality";
				status obsolete;
			}

			enum "rtl" {
				opd:help "RTL Group is a European entertainment company";
				status obsolete;
			}

			enum "rtmp" {
				opd:help "Real Time Messaging Protocol (RTMP) is a proprietary protocol developed by Adobe Systems for streaming audio, video and data over the Internet, between a Flash player and a server";
				status obsolete;
			}

			enum "rtp" {
				opd:help "RTP is the real-time transport protocol used to transmit real-time data, such as audio, video or simulation data, over multicast or unicast network services";
				status obsolete;
			}

			enum "rtsp" {
				opd:help "The Real Time Streaming Protocol (RTSP) is an application-level protocol for control over the delivery of data with real-time properties";
				status obsolete;
			}

			enum "rtvslo" {
				opd:help "Slovenian news portal";
				status obsolete;
			}

			enum "rubiconproject" {
				opd:help "Rubicon Project is an online advertising firm";
				status obsolete;
			}

			enum "rudaw" {
				opd:help "Kurd news portal";
				status obsolete;
			}

			enum "runescape" {
				opd:help "Massively Multiplayer Online Role Playing Game published by Jadex";
				status obsolete;
			}

			enum "rusers" {
				opd:help "The RUser's protocol provides a service that lists users currently logged on a remote server";
				status obsolete;
			}

			enum "ruten" {
				opd:help "Taiwanese auction website";
				status obsolete;
			}

			enum "rutracker" {
				opd:help "BitTorrent tracker search engine";
				status obsolete;
			}

			enum "ruv" {
				opd:help "Icelandic news portal";
				status obsolete;
			}

			enum "rvd" {
				opd:help "The rvd protocol (MIT Remote Virtual Disk Protocol) is found over the IP layer (IANA protocol number: 66)";
				status obsolete;
			}

			enum "ryanair" {
				opd:help "This classifies the HTTP traffic to the host ryanair.com";
				status obsolete;
			}

			enum "ryze" {
				opd:help "Ryze is a social network for entrepreneurs and other business professionals";
				status obsolete;
			}

			enum "s1ap" {
				opd:help "S1 Application Protocol (S1AP), as described in 3GPP TS 36.413 version 11.2.1 Release 11 (2013-02)";
				status obsolete;
			}

			enum "s_oman" {
				opd:help "Omani forum hosting website";
				status obsolete;
			}

			enum "saavn_music" {
				opd:help "Saavn is a streaming application providing free Indian and Bollywood music to listeners";
				status obsolete;
			}

			enum "sabah" {
				opd:help "Turkish news portal";
				status obsolete;
			}

			enum "sabameeting" {
				opd:help "Saba Meeting is a web conferencing and desktop sharing service";
				status obsolete;
			}

			enum "sabay" {
				opd:help "Cambodian news and information portal";
				status obsolete;
			}

			enum "saberindo" {
				opd:help "This classifies the HTTP and SSL traffic to the host saberindo.co.id";
				status obsolete;
			}

			enum "sabq" {
				opd:help "Saudi Arabian news portal";
				status obsolete;
			}

			enum "safaricom" {
				opd:help "Kenyan mobile and internet service provider website";
				status obsolete;
			}

			enum "safewebonline" {
				opd:help "Free internet monitoring and analytics application";
				status obsolete;
			}

			enum "sahafah" {
				opd:help "Yemeni news portal";
				status obsolete;
			}

			enum "saharamedias" {
				opd:help "Mauritanian news portal";
				status obsolete;
			}

			enum "sahibinden" {
				opd:help "Turkish online classified ads and e-commerce platform";
				status obsolete;
			}

			enum "saitebi" {
				opd:help "Georgian internet catalog";
				status obsolete;
			}

			enum "sakura_ne" {
				opd:help "Japanese professional web hosting services";
				status obsolete;
			}

			enum "salamnews" {
				opd:help "Azerbaijani news portal";
				status obsolete;
			}

			enum "salesforce" {
				opd:help "Salesforce is an on-line customer relationship management (CRM) web product";
				status obsolete;
			}

			enum "salesforce_chatter" {
				opd:help "Salesforce Chatter is a collaboration and instant messaging tool, part of the Salesforce CRM product";
				status obsolete;
			}

			enum "samanews" {
				opd:help "News web portal popular in Palestinian Territory";
				status obsolete;
			}

			enum "sameerbook" {
				opd:help "Jordanian news portal";
				status obsolete;
			}

			enum "samsung" {
				opd:help "Samsung is a South Korean multinational company";
				status obsolete;
			}

			enum "samsung_apps" {
				opd:help "Samsung Apps is an application store for Samsung mobile and TV users";
				status obsolete;
			}

			enum "samsung_update" {
				opd:help "Samsung Update classifies Samsung mobile device updates";
				status obsolete;
			}

			enum "sana" {
				opd:help "Syrian news portal";
				status obsolete;
			}

			enum "sanjesh" {
				opd:help "Website of the Iranian national education measurement and evaluation organisation";
				status obsolete;
			}

			enum "sanook" {
				opd:help "Thailandese website providing lottery games, music, chat, news, jobs, shopping and entertainment";
				status obsolete;
			}

			enum "sap" {
				opd:help "SAP is both a protocol and the name of an ERP application used by most companies";
				status obsolete;
			}

			enum "sapo" {
				opd:help "Mozambican web portal including mail, news, lifestyle";
				status obsolete;
			}

			enum "sarahanews" {
				opd:help "Jordanian news portal";
				status obsolete;
			}

			enum "sarayanews" {
				opd:help "Jordanian news portal";
				status obsolete;
			}

			enum "sat_expak" {
				opd:help "The sat_expak protocol (SATNET and Backroom EXPAK) is found over the IP layer (IANA protocol number: 64)";
				status obsolete;
			}

			enum "sat_mon" {
				opd:help "The sat_mon protocol (SATNET Monitoring) is found over the IP layer (IANA protocol number: 69)";
				status obsolete;
			}

			enum "savefile_com" {
				opd:help "(Deprecated) Classifies web browsing on the savefile.com Direct DownLoad links service";
				status obsolete;
			}

			enum "savefrom" {
				opd:help "File download service, allowing a user to download a media resource from many sites like Youtube, etc";
				status obsolete;
			}

			enum "sayclub" {
				opd:help "This classifies the HTTP and SSL traffic to the host sayclub.com";
				status obsolete;
			}

			enum "sbs" {
				opd:help "This classifies the HTTP traffic to the host sbs.co.kr";
				status obsolete;
			}

			enum "sbs_au" {
				opd:help "SBS is a media platform streaming in Australia";
				status obsolete;
			}

			enum "scc_sp" {
				opd:help "The scc_sp protocol (Semaphore Communications Sec. Pro.)";
				status obsolete;
			}

			enum "sccm" {
				opd:help "System Center Configuration Manager, is a systems management software product by Microsoft for managing large groups of computers running Windows, Mac OS X, Linux or UNIX, as well as various mobile operating systems";
				status obsolete;
			}

			enum "sccp" {
				opd:help "Skinny Client Control Protocol (SCCP) is a Cisco proprietary protocol used between Cisco Call Manager and Cisco VoIP phones";
				status obsolete;
			}

			enum "sccp_ss7" {
				opd:help "SCCP is a network layer protocol that provides routing, flow control or error detection services in SS7 networks";
				status obsolete;
			}

			enum "scenehd" {
				opd:help "BitTorrent tracker search engine";
				status obsolete;
			}

			enum "scheduled_tp" {
				opd:help "STP is a connection-oriented data transfer protocol";
				status obsolete;
			}

			enum "sciencestage" {
				opd:help "This classifies the HTTP traffic to the host sciencestage.com";
				status obsolete;
			}

			enum "scispace" {
				opd:help "This classifies the HTTP traffic to the host scispace.com";
				status obsolete;
			}

			enum "scorecardresearch" {
				opd:help "Scorecard Research provides a web data collection service";
				status obsolete;
			}

			enum "scotiabank" {
				opd:help "Bahamian banking website";
				status obsolete;
			}

			enum "scps" {
				opd:help "The scps protocol (SCPS) is found over the IP layer (IANA protocol number: 105)";
				status obsolete;
			}

			enum "scribd" {
				opd:help "This classifies the HTTP and SSL traffic to the host scribd.com";
				status obsolete;
			}

			enum "sde" {
				opd:help "Kenyan news and lifestyle related website";
				status obsolete;
			}

			enum "sdo" {
				opd:help "Chinese entertainment portal";
				status obsolete;
			}

			enum "sdrp" {
				opd:help "The sdrp protocol (Source Demand Routing Protocol) is found over the IP layer (IANA protocol number: 42)";
				status obsolete;
			}

			enum "searchnu" {
				opd:help "Browser toolbar search engine";
				status obsolete;
			}

			enum "secondlife" {
				opd:help "Secondlife is is an Internet-based virtual world which enables its users to interact with each other through motional avatars";
				status obsolete;
			}

			enum "secure_vmtp" {
				opd:help "The secure_vmtp protocol (SECURE_VMTP) is found over the IP layer (IANA protocol number: 82)";
				status obsolete;
			}

			enum "seeqpod" {
				opd:help "This classifies the HTTP traffic to the host intertrust.com";
				status obsolete;
			}

			enum "seesaa" {
				opd:help "Japanese web portal dedicated to smartphone applications and other websites";
				status obsolete;
			}

			enum "seesmic" {
				opd:help "(Deprecated) This classifies the HTTP traffic to the host seesmic.com";
				status obsolete;
			}

			enum "segye" {
				opd:help "Segye.com is a Korean newspaper website";
				status obsolete;
			}

			enum "sekindo" {
				opd:help "Sekindo is a digital platform for online video, display and mobile advertising";
				status obsolete;
			}

			enum "sendspace" {
				opd:help "File uploading service for large file sharing on web and mobile devices";
				status obsolete;
			}

			enum "senego" {
				opd:help "Senegalese national news portal";
				status obsolete;
			}

			enum "seneweb" {
				opd:help "Senegalese news portal";
				status obsolete;
			}

			enum "seoul_news" {
				opd:help "This classifies the HTTP traffic to the host seoul.co.kr";
				status obsolete;
			}

			enum "setopati" {
				opd:help "Nepali news portal";
				status obsolete;
			}

			enum "seznam" {
				opd:help "Czech internet web portal";
				status obsolete;
			}

			enum "sfr" {
				opd:help "SFR Telecom is a French telecommunications operator";
				status obsolete;
			}

			enum "sgcarmart" {
				opd:help "Singaporean online car market";
				status obsolete;
			}

			enum "shabiba" {
				opd:help "Omanian news portal";
				status obsolete;
			}

			enum "shaparak" {
				opd:help "Electronic payment company in Iran";
				status obsolete;
			}

			enum "share" {
				opd:help "Share is a free peer-to-peer application allowing users to exchange files anonymously and in a secure way";
				status obsolete;
			}

			enum "sharebee_com" {
				opd:help "Classifies web browsing on the sharebee.com Direct DownLoad links service";
				status obsolete;
			}

			enum "sharebox" {
				opd:help "BitTorrent tracker search engine";
				status obsolete;
			}

			enum "sharepoint" {
				opd:help "SharePoint is a web application platform designed as a centralized replacement for multiple web applications, like content management and document management systems";
				status obsolete;
			}

			enum "sharepoint_admin" {
				opd:help "SharePoint is a web application platform designed as a centralized replacement for multiple web applications, like content management and document management systems";
				status obsolete;
			}

			enum "sharepoint_blog" {
				opd:help "SharePoint is a web application platform designed as a centralized replacement for multiple web applications, like content management and document management systems";
				status obsolete;
			}

			enum "sharepoint_calendar" {
				opd:help "SharePoint is a web application platform designed as a centralized replacement for multiple web applications, like content management and document management systems";
				status obsolete;
			}

			enum "sharepoint_document" {
				opd:help "SharePoint is a web application platform designed as a centralized replacement for multiple web applications, like content management and document management systems";
				status obsolete;
			}

			enum "sharepoint_online" {
				opd:help "On-line version of the Microsoft Sharepoint services (included in Office 365)";
				status obsolete;
			}

			enum "sharereactor" {
				opd:help "BitTorrent tracker search engine";
				status obsolete;
			}

			enum "sharethemusic" {
				opd:help "(Deprecated) This classifies the HTTP traffic to the host sharethemusic.com";
				status obsolete;
			}

			enum "sharethrough" {
				opd:help "Sharethrough is an advertising software for publishers, app developers and advertisers";
				status obsolete;
			}

			enum "shasha" {
				opd:help "Palestinian news portal";
				status obsolete;
			}

			enum "shazam" {
				opd:help "Shazam is a popular music identification application for desktop and mobiles";
				status obsolete;
			}

			enum "shekulli" {
				opd:help "Albanian news portal";
				status obsolete;
			}

			enum "shelfari" {
				opd:help "This classifies the HTTP traffic to the host shelfari.com";
				status obsolete;
			}

			enum "shim6" {
				opd:help "The shim6 protocol (Shim6 Protocol) is found over the IP layer (IANA protocol number: 140)";
				status obsolete;
			}

			enum "shinhan" {
				opd:help "Shinhan Bank is a bank headquartered in Seoul, South Korea";
				status obsolete;
			}

			enum "shobiddak" {
				opd:help "Palestinian online classified ads";
				status obsolete;
			}

			enum "shop_com_mm" {
				opd:help "Myanmari online shopping website";
				status obsolete;
			}

			enum "shoutcast" {
				opd:help "Shoutcast is a protocol used to stream audio files over HTTP";
				status obsolete;
			}

			enum "showmypc" {
				opd:help "This classifies the HTTP traffic to the host showmypc.com";
				status obsolete;
			}

			enum "showtime_anytime" {
				opd:help "VoD service of SHOWTIME TV channel";
				status obsolete;
			}

			enum "shqiperiaime" {
				opd:help "Albanian news portal";
				status obsolete;
			}

			enum "shutterfly" {
				opd:help "This classifies the HTTP traffic to the host shutterfly.com";
				status obsolete;
			}

			enum "shutterstock" {
				opd:help "Shutterstock is a global marketplace for images, videos and music";
				status obsolete;
			}

			enum "siebel_crm" {
				opd:help "A customer relationship management (CRM) solution by Siebel Systems";
				status obsolete;
			}

			enum "sigmalive" {
				opd:help "Cypriot news portal";
				status obsolete;
			}

			enum "signal" {
				opd:help "Signal, formerly BrightTag, is a cross-channel marketing company";
				status obsolete;
			}

			enum "signal_private_messenger" {
				opd:help "Open Whisper Systems (OWS) instant messaging mobile application that implements the Signal secured protocol";
				status obsolete;
			}

			enum "silverlight" {
				opd:help "Silverlight is a Microsoft web browser plugin designed to render programmable animations and to stream videos";
				status obsolete;
			}

			enum "simperium" {
				opd:help "Simperium is a service for developers to move data everywhere it's needed, instantly and automatically";
				status obsolete;
			}

			enum "simple_msg_p" {
				opd:help "The simple_msg_p protocol (Simple Message Protocol) is found over the IP layer (IANA protocol number: 121)";
				status obsolete;
			}

			enum "simpleupload_net" {
				opd:help "(Deprecated) Classifies web browsing on the simpleupload.net Direct DownLoad links service";
				status obsolete;
			}

			enum "sina" {
				opd:help "Sina is a Chinese chat client similar to MSN Messenger or ICQ";
				status obsolete;
			}

			enum "sina_blog" {
				opd:help "Sina blog hosting service";
				status obsolete;
			}

			enum "sina_finance" {
				opd:help "Sina finance news portal";
				status obsolete;
			}

			enum "sina_news" {
				opd:help "Chinese news portal";
				status obsolete;
			}

			enum "sina_video" {
				opd:help "Chinese on-line video streaming and VOD service";
				status obsolete;
			}

			enum "sina_webmail" {
				opd:help "Sina Webmail is a Chinese webmail";
				status obsolete;
			}

			enum "sina_weibo" {
				opd:help "Sina Weibo is a Chinese microblogging website";
				status obsolete;
			}

			enum "sinoptik" {
				opd:help "Weather forecast website in Bulgaria";
				status obsolete;
			}

			enum "siol" {
				opd:help "Slovenian news portal";
				status obsolete;
			}

			enum "sip" {
				opd:help "Session Initiation Protocol (SIP) is the Internet Engineering Task Force's (IETF's) standard for multimedia conferencing over IP";
				status obsolete;
			}

			enum "sip_soap" {
				opd:help "SIP-SOAP is an extension to the standard SIP protocol allowing for SOAP messages to be passed over a SIP connection";
				status obsolete;
			}

			enum "sistic" {
				opd:help "Sistic is a Singaporean online events tickets booking website";
				status obsolete;
			}

			enum "sitel" {
				opd:help "News web portal popular in Macedonia";
				status obsolete;
			}

			enum "sizmek" {
				opd:help "Sizmek (MediaMind, Eyeblaster) is an advertising management company";
				status obsolete;
			}

			enum "skee_ball_arcade" {
				opd:help "Mobile game";
				status obsolete;
			}

			enum "skelbiu" {
				opd:help "Lithuanian online classified ads and trading website";
				status obsolete;
			}

			enum "skip" {
				opd:help "The skip protocol (SKIP) is found over the IP layer (IANA protocol number: 57)";
				status obsolete;
			}

			enum "skroutz" {
				opd:help "Greek price comparator";
				status obsolete;
			}

			enum "sky" {
				opd:help "This classifies the HTTP traffic to the host www.sky.com";
				status obsolete;
			}

			enum "sky_player" {
				opd:help "Sky Go is an online TV service from Sky that allows watching video content from Mac, Windows PC, most mobile phones or video game consoles";
				status obsolete;
			}

			enum "skyblog" {
				opd:help "SkyBlog is a website where users can have blogs";
				status obsolete;
			}

			enum "skycn" {
				opd:help "This classifies the HTTP traffic to the host skycn.com";
				status obsolete;
			}

			enum "skydrive" {
				opd:help "(Deprecated) Skydrive was a personal storage platform for Windows users, now replaced by Microsoft OneDrive";
				status obsolete;
			}

			enum "skydrive_login" {
				opd:help "(Deprecated) On-line file storage service owned by Microsoft, now replaced by Microsoft OneDrive";
				status obsolete;
			}

			enum "skynewsarabia" {
				opd:help "International news portal focused on the middle east region";
				status obsolete;
			}

			enum "skype" {
				opd:help "Skype is a widely used voice over IP protocol";
				status obsolete;
			}

			enum "skyrock" {
				opd:help "(Deprecated) This classifies the HTTP traffic to the host www.skyrock.com";
				status obsolete;
			}

			enum "slack" {
				opd:help "Slack is an online team collaboration tool, featuring both a web browser application and mobile apps";
				status obsolete;
			}

			enum "slacker" {
				opd:help "Slacker Radio is an online music streaming service available from web browser and mobile application";
				status obsolete;
			}

			enum "slando" {
				opd:help "(Deprecated) Belarusian free classified ads";
				status obsolete;
			}

			enum "sld" {
				opd:help "Web portal about healthcare, with news and resources, from Cuba";
				status obsolete;
			}

			enum "slideshare" {
				opd:help "SlideShare is a famous slidepack hosting web service, owned by LinkedIn Corporation";
				status obsolete;
			}

			enum "slingbox" {
				opd:help "Slingbox is a streaming protocol over the Internet used to watch and control TV shows received from your home devices";
				status obsolete;
			}

			enum "slsk" {
				opd:help "Soulseek is a peer-to-peer protocol";
				status obsolete;
			}

			enum "sm" {
				opd:help "The sm protocol (SM) is found over the IP layer (IANA protocol number: 122)";
				status obsolete;
			}

			enum "smaato" {
				opd:help "Smaato is a real-time advertising platform for mobile publishers and app developers";
				status obsolete;
			}

			enum "smartadserver" {
				opd:help "Smart AdServer provides advertising services";
				status obsolete;
			}

			enum "smartalk" {
				opd:help "SMARTalk is a Japanese VoIP application for Smartphones which allows you to save money when making calls";
				status obsolete;
			}

			enum "smb" {
				opd:help "The Server Message Block protocol (SMB) provides a method for client applications to read and write to files and to request services from server programs in a computers network";
				status obsolete;
			}

			enum "smb_direct" {
				opd:help "SMB Direct protocol is a transmission protocol which allows higher throughput when exchanging data using SMB";
				status obsolete;
			}

			enum "sme" {
				opd:help "Slovak news portal";
				status obsolete;
			}

			enum "smh" {
				opd:help "News streaming site in Australia which features latest local and International news, business, sport, entertainment etc";
				status obsolete;
			}

			enum "smpp" {
				opd:help "SMPP is a telecommunications industry protocol for exchanging SMS messages between SMS peer entities";
				status obsolete;
			}

			enum "smtp" {
				opd:help "The Simple Mail Transfer Protocol (SMTP) is a protocol used for transferring mail reliably and efficiently";
				status obsolete;
			}

			enum "smtps" {
				opd:help "Secure version of the SMTP protocol";
				status obsolete;
			}

			enum "sna" {
				opd:help "SNA (Systems Network Architecture) is IBM's mainframe network standard";
				status obsolete;
			}

			enum "snapchat" {
				opd:help "Snapchat is a photo/video sharing service";
				status obsolete;
			}

			enum "snmp" {
				opd:help "SNMP is a request/response protocol that communicates management information between two types of SNMP software entities: SNMP applications (also called SNMP managers) and SNMP agents";
				status obsolete;
			}

			enum "snp" {
				opd:help "The snp protocol (Sitara Networks Protocol) is found over the IP layer (IANA protocol number: 109)";
				status obsolete;
			}

			enum "snpp" {
				opd:help "This protocol defines a method by which a pager can receive a message over the Internet";
				status obsolete;
			}

			enum "soap" {
				opd:help "SOAP is a lightweight protocol based on XML intended for exchanging structured information in a decentralized, distributed environment";
				status obsolete;
			}

			enum "socialcam" {
				opd:help "(Deprecated) Socialcam was an application to capture and share videos on mobile handsets, which was shut down on October 2015";
				status obsolete;
			}

			enum "socialtv" {
				opd:help "This classifies the HTTP traffic to the host srv.sixdegs.com";
				status obsolete;
			}

			enum "socialvibe" {
				opd:help "(Deprecated) This used to classify the HTTP traffic to the host socialvibe.com";
				status obsolete;
			}

			enum "socks2http" {
				opd:help "Socks2http is a client software aiming to make a tunnel";
				status obsolete;
			}

			enum "socks4" {
				opd:help "Socks 4 is an authentication protocol";
				status obsolete;
			}

			enum "socks5" {
				opd:help "Socks 5 is an authentication protocol";
				status obsolete;
			}

			enum "soft4fun" {
				opd:help "Hardware and software news site";
				status obsolete;
			}

			enum "softbank" {
				opd:help "SoftBank network operator services";
				status obsolete;
			}

			enum "softonic" {
				opd:help "Softonic.com is a software download portal based in Barcelona";
				status obsolete;
			}

			enum "softros_messenger" {
				opd:help "Softros Messenger is a LAN messaging and file transfer application";
				status obsolete;
			}

			enum "sogou" {
				opd:help "This classifies the HTTP traffic to the host sogou.com";
				status obsolete;
			}

			enum "sohu" {
				opd:help "Sohu services (except blogging classified in sohu_blog)";
				status obsolete;
			}

			enum "sohu_blog" {
				opd:help "Sohu blog hosting service";
				status obsolete;
			}

			enum "soku" {
				opd:help "This classifies the HTTP traffic to the host soku.com";
				status obsolete;
			}

			enum "solarwinds" {
				opd:help "SolarWinds Inc. develops enterprise information technology (IT) infrastructure management software for IT professionals";
				status obsolete;
			}

			enum "somalijobs" {
				opd:help "Job seeking website in Somalia";
				status obsolete;
			}

			enum "somon" {
				opd:help "Classified ads website in Tajikistan";
				status obsolete;
			}

			enum "somud" {
				opd:help "SoMud is a BitTorrent client";
				status obsolete;
			}

			enum "sonet_ne" {
				opd:help "Japanese web portal of the internet provider So-net";
				status obsolete;
			}

			enum "sonico" {
				opd:help "This classifies the HTTP traffic to the host sonico.com";
				status obsolete;
			}

			enum "sonmp" {
				opd:help "Nortel/SynOptics Network Management Protocol is a proprietary Nortel Networks management protocol";
				status obsolete;
			}

			enum "sonobi" {
				opd:help "Sonobi is an ad technology developer that designs advertising tools and solutions";
				status obsolete;
			}

			enum "sopcast" {
				opd:help "Sopcast is a video streaming service based on a peer-to-peer protocol : SOP (Streaming Over Peer-to-peer)";
				status obsolete;
			}

			enum "sophos_update" {
				opd:help "Sophos antivirus update protocol";
				status obsolete;
			}

			enum "soribada" {
				opd:help "This classifies the HTTP traffic to the host kpop.soribada.com";
				status obsolete;
			}

			enum "soso" {
				opd:help "This classifies the HTTP traffic to the host soso.com";
				status obsolete;
			}

			enum "soufun" {
				opd:help "This classifies the HTTP traffic to the host soufun.com";
				status obsolete;
			}

			enum "soundcloud" {
				opd:help "SoundCloud is an online audio distribution platform where users can upload, promote and share their sounds with others";
				status obsolete;
			}

			enum "souq" {
				opd:help "Saudi Arabian ecommerce website";
				status obsolete;
			}

			enum "sourceforge" {
				opd:help "Sourceforge is a famous web based code repository for open source software development";
				status obsolete;
			}

			enum "southwest" {
				opd:help "This classifies the HTTP traffic to the host southwest.com";
				status obsolete;
			}

			enum "soy502" {
				opd:help "Guatemalan news portal";
				status obsolete;
			}

			enum "sp" {
				opd:help "ISO 8327-1/X.225 OSI Session Protocol (SP)";
				status obsolete;
			}

			enum "spdy" {
				opd:help "SPDY is an open networking protocol developed primarily at Google for transporting web content";
				status obsolete;
			}

			enum "speedtest" {
				opd:help "Website and mobile application for testing both bandwidth and latency of any internet connection";
				status obsolete;
			}

			enum "spid" {
				opd:help "SPID (Statistical Protocol IDentification) is a statistical classification engine, used to identify encrypted or obfuscated streams from advanced Peer-to-peer or VPN protocols (ex: BitTorrent RC4 streams)";
				status obsolete;
			}

			enum "spiegel" {
				opd:help "This classifies the HTTP traffic to the host spiegel.de";
				status obsolete;
			}

			enum "splunk" {
				opd:help "Splunk is an American multinational corporation based in San Francisco, California, that produces software for searching, monitoring, and analyzing machine-generated big data, via a web-style interface";
				status obsolete;
			}

			enum "sportal" {
				opd:help "Bulgarian sports related website";
				status obsolete;
			}

			enum "sportchosun" {
				opd:help "This classifies the HTTP traffic to the host sportschosun.com";
				status obsolete;
			}

			enum "sportpesa" {
				opd:help "Kenyan betting platform, sponsor of Kenya's official football League";
				status obsolete;
			}

			enum "sportsillustrated" {
				opd:help "News portal dedicated to sports";
				status obsolete;
			}

			enum "sportsseoul" {
				opd:help "This classifies the HTTP traffic to the host sportsseoul.com";
				status obsolete;
			}

			enum "spotflux" {
				opd:help "VPN service which offers to protect the Internet connections of its users";
				status obsolete;
			}

			enum "spotify" {
				opd:help "Spotify is an application of musical streaming";
				status obsolete;
			}

			enum "spotxchange" {
				opd:help "SpotX provides a video advertising platform for internet publishers";
				status obsolete;
			}

			enum "spredfast" {
				opd:help "Spredfast is an enterprise social media marketing platform";
				status obsolete;
			}

			enum "sprint" {
				opd:help "This classifies the HTTP traffic to the host sprint.com";
				status obsolete;
			}

			enum "sprite_rpc" {
				opd:help "The sprite_rpc protocol (Sprite RPC Protocol) is found over the IP layer (IANA protocol number: 90)";
				status obsolete;
			}

			enum "sps" {
				opd:help "The sps protocol (Secure Packet Shield) is found over the IP layer (IANA protocol number: 130)";
				status obsolete;
			}

			enum "spynet" {
				opd:help "Malware and spyware signature detection network used by Windows Defender and Microsoft Security Essentials";
				status obsolete;
			}

			enum "sqli" {
				opd:help "The SQLI protocol (Structured Query Language Interface) is a proprietary protocol seemingly used exclusively in IBM Informix servers";
				status obsolete;
			}

			enum "squirrelmail" {
				opd:help "SquirrelMail is a web-based email application written in the PHP scripting language";
				status obsolete;
			}

			enum "srp" {
				opd:help "The srp protocol (SpectraLink Radio Protocol) is found over the IP layer (IANA protocol number: 119)";
				status obsolete;
			}

			enum "srvloc" {
				opd:help "Service Location Protocol is a decentralized, lightweight, scalable and extensible protocol for service discovery within a local area network";
				status obsolete;
			}

			enum "ss" {
				opd:help "Latvian online classified ads";
				status obsolete;
			}

			enum "sscopmce" {
				opd:help "The sscopmce protocol (Service Specific Connection Oriented Protocol for M-Cast Env) is found over the IP layer (IANA protocol number: 128)";
				status obsolete;
			}

			enum "ssdp" {
				opd:help "Simple Service Discovery Protocol (SSDP) provides a mechanism whereby network clients can discover desired network services";
				status obsolete;
			}

			enum "ssh" {
				opd:help "Secure Shell (SSH), sometimes known as Secure Socket Shell, is a UNIX-based command interface and a protocol for obtaining secure access to a remote computer";
				status obsolete;
			}

			enum "ssl" {
				opd:help "Secure Sockets Layer (SSL) is a commonly-used protocol for managing the security of a message transmission on the Internet";
				status obsolete;
			}

			enum "st" {
				opd:help "The st protocol (Stream) is found over the IP layer (IANA protocol number: 5)";
				status obsolete;
			}

			enum "st_lucia_news_online" {
				opd:help "Local news web portal from Saint Lucia island";
				status obsolete;
			}

			enum "stackexchange" {
				opd:help "Stack Exchange is a network of English-language sites for collaborative editing questions and answers, each dealing with a particular theme";
				status obsolete;
			}

			enum "stackoverflow" {
				opd:help "Stack Overflow is a website offering questions and answers on a wide range of topics concerning computer programming";
				status obsolete;
			}

			enum "stafaband" {
				opd:help "This classifies the HTTP traffic to the host stafaband.info";
				status obsolete;
			}

			enum "stagevu" {
				opd:help "This classifies the HTTP traffic to the host stagevu.com";
				status obsolete;
			}

			enum "standardmedia" {
				opd:help "Kenyan news portal";
				status obsolete;
			}

			enum "starnieuws" {
				opd:help "Non-stop news from Suriname, featuring videos, articles, documents";
				status obsolete;
			}

			enum "startimes" {
				opd:help "Arabic forum hosting site";
				status obsolete;
			}

			enum "state_bank_of_india" {
				opd:help "Internet portal of the SBI Indian bank";
				status obsolete;
			}

			enum "stayfriends" {
				opd:help "Stayfriends.de is a social network";
				status obsolete;
			}

			enum "stealthnet" {
				opd:help "Stealthnet is a file sharing application between two or more hosts";
				status obsolete;
			}

			enum "steam" {
				opd:help "Steam is a digital distribution, digital rights management, multiplayer and communications platform developed by Valve Corporation";
				status obsolete;
			}

			enum "stick_cricket" {
				opd:help "Mobile game";
				status obsolete;
			}

			enum "stickam" {
				opd:help "This classifies the HTTP traffic to the host stickam.com";
				status obsolete;
			}

			enum "stickyads" {
				opd:help "Stickyads is a video platform for publishers in Europe";
				status obsolete;
			}

			enum "stockq" {
				opd:help "Taiwanese stock market information";
				status obsolete;
			}

			enum "storytel" {
				opd:help "Storytel is a digital subscription service that enables audio book listening from browser or smartphones";
				status obsolete;
			}

			enum "streamaudio" {
				opd:help "This classifies the HTTP traffic to the host streamaudio.com";
				status obsolete;
			}

			enum "streamrail" {
				opd:help "StreamRail is a video advertising technology platform";
				status obsolete;
			}

			enum "studivz" {
				opd:help "This classifies the HTTP traffic to the host studivz.net";
				status obsolete;
			}

			enum "stuff" {
				opd:help "New Zealander news portal";
				status obsolete;
			}

			enum "stumbleupon" {
				opd:help "This classifies the HTTP traffic to the host stumbleupon.com";
				status obsolete;
			}

			enum "stun" {
				opd:help "STUN (Session Traversal Utilities for NAT) allows a client behind a NAT to establish UDP tunnels between two hosts";
				status obsolete;
			}

			enum "stupid_videos" {
				opd:help "Streaming website for funny videos";
				status obsolete;
			}

			enum "sua" {
				opd:help "This protocol defines the transport of SCCP signalization over an IP network through SCTP";
				status obsolete;
			}

			enum "subway_surfers" {
				opd:help "Mobile game";
				status obsolete;
			}

			enum "sugar_crm" {
				opd:help "Sugar CRM, a client relationship management solution";
				status obsolete;
			}

			enum "sugar_sync" {
				opd:help "On-line file backup and sync service";
				status obsolete;
			}

			enum "sugklonistiko" {
				opd:help "News and entertainment web portal in Greece";
				status obsolete;
			}

			enum "sulit" {
				opd:help "(Deprecated) Filipino online classified ads";
				status obsolete;
			}

			enum "sun_nd" {
				opd:help "The sun_nd protocol (SUN ND PROTOCOL_Temporary) is found over the IP layer (IANA protocol number: 77)";
				status obsolete;
			}

			enum "sun_online" {
				opd:help "SunFM Radio's online streaming and news portal";
				status obsolete;
			}

			enum "suning" {
				opd:help "Chinese online shopping";
				status obsolete;
			}

			enum "super" {
				opd:help "Prague based agency represents models from Czech and Slovak Republic";
				status obsolete;
			}

			enum "super_mario_run" {
				opd:help "Online mobile game by Nintendo";
				status obsolete;
			}

			enum "supercell" {
				opd:help "Supercell is a video game developer and editor";
				status obsolete;
			}

			enum "suppersoccer" {
				opd:help "This classifies the HTTP traffic to the host m.supersoccer.co.id";
				status obsolete;
			}

			enum "suresome" {
				opd:help "Suresome allows to increase browsing capabilities with a SSL proxy";
				status obsolete;
			}

			enum "surrogafier" {
				opd:help "This classifies the HTTP traffic to the hosts surrogafier.info and go.vfserver.com";
				status obsolete;
			}

			enum "surveymonkey" {
				opd:help "This classifies the HTTP traffic to the host surveymonkey.com";
				status obsolete;
			}

			enum "svcctl" {
				opd:help "This protocol is used to control remotely Windows services";
				status obsolete;
			}

			enum "svn" {
				opd:help "Subversion, version control system";
				status obsolete;
			}

			enum "svtplay" {
				opd:help "Sveriges Television video-on-demand website";
				status obsolete;
			}

			enum "swedbank" {
				opd:help "Swedbank online banking and investment web portal";
				status obsolete;
			}

			enum "swepiracy" {
				opd:help "BitTorrent tracker search engine";
				status obsolete;
			}

			enum "swipe" {
				opd:help "The swipe protocol (IP with Encryption) is found over the IP layer (IANA protocol number: 53)";
				status obsolete;
			}

			enum "switch_concepts" {
				opd:help "Switch is a UK based advertising system";
				status obsolete;
			}

			enum "sybase" {
				opd:help "Sybase protocols are used to exchange messages (namely authentication and SQL queries) between database clients and servers developed by the Sybase Company";
				status obsolete;
			}

			enum "symantec" {
				opd:help "Symantec Corporation makes security, storage, backup and availability software";
				status obsolete;
			}

			enum "sync" {
				opd:help "The Sync protocol is an RPC service allowing data synchronisation";
				status obsolete;
			}

			enum "synflood" {
				opd:help "(Deprecated) This plug-in is no longer supported";
				status obsolete;
			}

			enum "syri" {
				opd:help "Popular news website in Albania";
				status obsolete;
			}

			enum "syslog" {
				opd:help "Syslog protocol is used for the transmission of event notification messages across networks between a client and a server";
				status obsolete;
			}

			enum "t38" {
				opd:help "This protocol is used to exchanges FAXes on top on TCP/IP";
				status obsolete;
			}

			enum "t_online" {
				opd:help "T-Online German ISP web portal";
				status obsolete;
			}

			enum "tabelog" {
				opd:help "Online Japanese restaurant guide";
				status obsolete;
			}

			enum "taboola" {
				opd:help "Taboola is a content marketing platform that provides a web widget to content creators on their website";
				status obsolete;
			}

			enum "tacacs_plus" {
				opd:help "TACACS+ (Terminal Access Controller Access-Control System Plus) is a Cisco Systems proprietary protocol which provides access control for routers, network access servers and other networked computing devices via one or more centralized servers";
				status obsolete;
			}

			enum "tagged" {
				opd:help "Tagged is a social networking website, enabling users to connect to relatives, friends, or unknown people";
				status obsolete;
			}

			enum "tagoo" {
				opd:help "This classifies the HTTP traffic to the host tagoo.ru";
				status obsolete;
			}

			enum "tahiti_infos" {
				opd:help "Tahitian news portal";
				status obsolete;
			}

			enum "taiwanlottery" {
				opd:help "Taiwan lottery website";
				status obsolete;
			}

			enum "tajfile" {
				opd:help "Direct Download pirate movie portal in Tajikistan";
				status obsolete;
			}

			enum "takealot" {
				opd:help "Online shopping portal in South Africa";
				status obsolete;
			}

			enum "taku_file_bin" {
				opd:help "Japanese Direct Download web platform, allowing free sharing of large files";
				status obsolete;
			}

			enum "talabat" {
				opd:help "Large online food delivery platform in Kuwait, Saudi Arabia, Bahrain, UAE, Oman and Qatar";
				status obsolete;
			}

			enum "talenttrove" {
				opd:help "Lafango (aka TalentTrove) is a media sharing and social network website";
				status obsolete;
			}

			enum "talkbiznow" {
				opd:help "This classifies the HTTP traffic to the host talkbiznow.com";
				status obsolete;
			}

			enum "taltopia" {
				opd:help "This classifies the HTTP traffic to the host taltopia.com";
				status obsolete;
			}

			enum "tamilthunder_com" {
				opd:help "BitTorrent tracker search engine";
				status obsolete;
			}

			enum "tamtaminfo" {
				opd:help "News web portal in Niger";
				status obsolete;
			}

			enum "tango" {
				opd:help "Tango is an embedded smartphone application dedicated to audio/video-conference";
				status obsolete;
			}

			enum "tanx" {
				opd:help "Taobao Ad Network and Exchange provides advertising services";
				status obsolete;
			}

			enum "taobao" {
				opd:help "Taobao is a Chinese shopping website";
				status obsolete;
			}

			enum "tapatalk" {
				opd:help "Mobile app which allows to browse forums";
				status obsolete;
			}

			enum "tapchisao" {
				opd:help "News and entertainment portal from Vietnam";
				status obsolete;
			}

			enum "taqadoumi" {
				opd:help "Famous news blog in Mauritania";
				status obsolete;
			}

			enum "taringa" {
				opd:help "This classifies the HTTP traffic to the host taringa.net";
				status obsolete;
			}

			enum "tasweernews" {
				opd:help "Jordanian news portal";
				status obsolete;
			}

			enum "tawary" {
				opd:help "Mauritanian news portal";
				status obsolete;
			}

			enum "tayara" {
				opd:help "Tunisian classified ads website, part of the Schibsted Classified Media (SCM) group";
				status obsolete;
			}

			enum "tayyar" {
				opd:help "Lebanese news portal";
				status obsolete;
			}

			enum "tbs" {
				opd:help "Website to stream funny TV shows and movies";
				status obsolete;
			}

			enum "tcf" {
				opd:help "The tcf protocol (TCF) is found over the IP layer (IANA protocol number: 87)";
				status obsolete;
			}

			enum "tchatche" {
				opd:help "Tchatche is an instant messaging website";
				status obsolete;
			}

			enum "tcp_over_dns" {
				opd:help "Tcp-over-dns contains a special DNS server and a special DNS client";
				status obsolete;
			}

			enum "tds" {
				opd:help "TDS protocol is used to communicate between SQL applications and a SQL Server";
				status obsolete;
			}

			enum "teachertube" {
				opd:help "This classifies the HTTP and SSL traffic to the host teachertube.com";
				status obsolete;
			}

			enum "teachstreet" {
				opd:help "This classifies the HTTP traffic to the host teachstreet.com";
				status obsolete;
			}

			enum "teads" {
				opd:help "Teads is a video advertising platform";
				status obsolete;
			}

			enum "tealium" {
				opd:help "Tealium sells enterprise tag management and marketing software";
				status obsolete;
			}

			enum "teamspeak" {
				opd:help "The proprietary TeamSpeak2 protocol is used by gamers and oriented TeamSpeak2 VoIP software";
				status obsolete;
			}

			enum "teamspeak_v3" {
				opd:help "TeamSpeak 3 continues the legacy of the original TeamSpeak communication system";
				status obsolete;
			}

			enum "teamviewer" {
				opd:help "TeamViewer is an application that enables a connection to a remote computer in order to perform maintenance operations";
				status obsolete;
			}

			enum "tebyan" {
				opd:help "Popular infotainment portal in Iran";
				status obsolete;
			}

			enum "techinline" {
				opd:help "Remote service for viewing, diagnosing and fixing technical issues on desktop machines";
				status obsolete;
			}

			enum "telegraaf" {
				opd:help "Dutch news web portal";
				status obsolete;
			}

			enum "telegraf" {
				opd:help "Serbian web portal";
				status obsolete;
			}

			enum "telegrafi" {
				opd:help "Albanian news and media portal";
				status obsolete;
			}

			enum "telegram" {
				opd:help "Telegram is an instant messaging protocol like Whatsapp";
				status obsolete;
			}

			enum "telestream" {
				opd:help "Telestream, Inc. is an American privately held provider of software and hardware products for video capture, encoding, transcoding, and network-based delivery";
				status obsolete;
			}

			enum "teletica" {
				opd:help "TV calendar service and news web portal in Costa Rica";
				status obsolete;
			}

			enum "telnet" {
				opd:help "Telnet provides a fairly general, bi-directional, eight-bit byte oriented communications facility";
				status obsolete;
			}

			enum "telnets" {
				opd:help "Secure version of the Telnet";
				status obsolete;
			}

			enum "teltel" {
				opd:help "VoIP software which allows calling other teltel users";
				status obsolete;
			}

			enum "tempointeraktif" {
				opd:help "This classifies the HTTP traffic to the hosts tempointeraktif.com and tempo.co";
				status obsolete;
			}

			enum "tencent" {
				opd:help "Instant communications service provider in Asia, providing corporate and personal instant messaging, online entertainment and value-added services";
				status obsolete;
			}

			enum "teredo" {
				opd:help "The Teredo protocol enables IPv6 tunneling over UDP, traversing NATs, and with minimum over-head";
				status obsolete;
			}

			enum "tf1" {
				opd:help "TF1.fr is the website of a private national French TV channel";
				status obsolete;
			}

			enum "tftp" {
				opd:help "Trivial File Transfer Protocol (TFTP) is a file transfer protocol that is simpler to use than the File Transfer Protocol (FTP) but that proposes less features";
				status obsolete;
			}

			enum "tgbus" {
				opd:help "Chinese games portal";
				status obsolete;
			}

			enum "thadinatin" {
				opd:help "Popular infotainment portal in Myanmar";
				status obsolete;
			}

			enum "the_auteurs" {
				opd:help "(Deprecated) This used to classify the HTTP traffic to the host theauteurs.com";
				status obsolete;
			}

			enum "the_simpsons_tapped_out" {
				opd:help "Mobile game (EA Games)";
				status obsolete;
			}

			enum "the_star" {
				opd:help "Kenyan web portal featuring world, business, sport, opinion, health news";
				status obsolete;
			}

			enum "theladbible" {
				opd:help "Entertainment website with thousands of unique photo galleries and videos";
				status obsolete;
			}

			enum "themasports" {
				opd:help "Cypriot sports related website";
				status obsolete;
			}

			enum "thepiratebay" {
				opd:help "A popular Swedish Torrent indexing website";
				status obsolete;
			}

			enum "thethao247" {
				opd:help "Football news site mostly watched in Vietnam";
				status obsolete;
			}

			enum "thevideos" {
				opd:help "Free file upload service";
				status obsolete;
			}

			enum "think" {
				opd:help "Macedonian news portal";
				status obsolete;
			}

			enum "thithtoolwin" {
				opd:help "Myanmar news portal";
				status obsolete;
			}

			enum "three" {
				opd:help "This classifies the HTTP and SSL traffic to the hosts three.co.id and tri.co.id";
				status obsolete;
			}

			enum "threema" {
				opd:help "Threema is an instant messaging mobile application focused on confidentiality";
				status obsolete;
			}

			enum "thunder" {
				opd:help "Xunlei/Thunder is a Chinese multi-protocol download manager";
				status obsolete;
			}

			enum "ti_les_twra" {
				opd:help "Buzzing content web portal popular in Greece";
				status obsolete;
			}

			enum "tianya" {
				opd:help "Popular internet forums in China";
				status obsolete;
			}

			enum "tibcordv" {
				opd:help "This protocol is used in the bank sector";
				status obsolete;
			}

			enum "ticketmonster" {
				opd:help "This classifies the HTTP traffic to the host ticketmonster.co.kr";
				status obsolete;
			}

			enum "tidal" {
				opd:help "Tidal is a high-fidelity music and video clips streaming service for PC and mobile devices";
				status obsolete;
			}

			enum "tidaltv" {
				opd:help "This classifies the HTTP traffic to the host portal.tidaltv.com";
				status obsolete;
			}

			enum "tiempo" {
				opd:help "Honduran news portal";
				status obsolete;
			}

			enum "tigerair" {
				opd:help "Singaporian online travel agency";
				status obsolete;
			}

			enum "time" {
				opd:help "This protocol provides a site-independent, machine readable date and time";
				status obsolete;
			}

			enum "timesofmalta" {
				opd:help "Maltese news portal";
				status obsolete;
			}

			enum "timesofoman" {
				opd:help "Omanian news portal";
				status obsolete;
			}

			enum "tinder" {
				opd:help "Online dating application";
				status obsolete;
			}

			enum "tistory" {
				opd:help "This classifies the HTTP traffic to the host tistory.com";
				status obsolete;
			}

			enum "tlsp" {
				opd:help "The tlsp protocol (Transport Layer Security) is found over the IP layer (IANA protocol number: 56)";
				status obsolete;
			}

			enum "tmall" {
				opd:help "This classifies the HTTP traffic to the host tmall.com";
				status obsolete;
			}

			enum "tn8" {
				opd:help "Nicaraguan news portal";
				status obsolete;
			}

			enum "tns" {
				opd:help "Transparent Network Service (TNS) is the Oracle (version 8 or higher) networking technology that provides a single application interface to all industry-standard networking protocols";
				status obsolete;
			}

			enum "tntdrama" {
				opd:help "TNTDrama.com is a part of Turner Entertainment Digital";
				status obsolete;
			}

			enum "tnvip" {
				opd:help "Telnet VIP is an emulation of the Telnet protocol for VIP (Visual Information Projection) terminals";
				status obsolete;
			}

			enum "to_mati" {
				opd:help "Greek web portal";
				status obsolete;
			}

			enum "tocmai" {
				opd:help "Romanian classified ads website";
				status obsolete;
			}

			enum "toggle" {
				opd:help "Singaporian video streaming website";
				status obsolete;
			}

			enum "tokbox" {
				opd:help "This classifies the HTTP traffic to the host tokbox.com";
				status obsolete;
			}

			enum "tokobagus" {
				opd:help "This classifies the HTTP and SSL traffic to the host tokobagus.com";
				status obsolete;
			}

			enum "tokopedia" {
				opd:help "Indonesian general online store";
				status obsolete;
			}

			enum "tonaton" {
				opd:help "Ghanean classified ads website";
				status obsolete;
			}

			enum "top_channel" {
				opd:help "Albanina TV streaming website";
				status obsolete;
			}

			enum "topfmradio" {
				opd:help "Famous radio station in Mauritius";
				status obsolete;
			}

			enum "topky" {
				opd:help "Slovak news portal";
				status obsolete;
			}

			enum "topvideo" {
				opd:help "Video streaming webportal in Tajikistan";
				status obsolete;
			}

			enum "topvldeo" {
				opd:help "Video sharing and streaming platform in Tajikistan";
				status obsolete;
			}

			enum "tor" {
				opd:help "Tor is an application that intends to provide online anonymity";
				status obsolete;
			}

			enum "tor2web" {
				opd:help "Tor2web is a project intended to give Internet users access to Tor Onion Services without the need to use Tor Browser";
				status obsolete;
			}

			enum "torg" {
				opd:help "Uzbek classified ads";
				status obsolete;
			}

			enum "tori" {
				opd:help "Classified ads website in Finland";
				status obsolete;
			}

			enum "torrent9" {
				opd:help "Popular torrent file (P2P) search engine and download website";
				status obsolete;
			}

			enum "torrentdownloads" {
				opd:help "BitTorrent tracker search engine";
				status obsolete;
			}

			enum "torrentkim5" {
				opd:help "Torrent file (P2P) search engine and download website popular in South Korea";
				status obsolete;
			}

			enum "torrentz" {
				opd:help "Free torrent meta-search engine";
				status obsolete;
			}

			enum "tothemaonline" {
				opd:help "Cypriot news portal";
				status obsolete;
			}

			enum "touch" {
				opd:help "Touch is a cross-platform application providing free text, picture, and video messaging";
				status obsolete;
			}

			enum "tower_of_saviors" {
				opd:help "Mobile game";
				status obsolete;
			}

			enum "tp_plus_plus" {
				opd:help "The tp_plus_plus protocol (TP++ Transport Protocol) is found over the IP layer (IANA protocol number: 39)";
				status obsolete;
			}

			enum "trackingclick" {
				opd:help "Web analytics services located in Bangladesh";
				status obsolete;
			}

			enum "trademe" {
				opd:help "New Zealander online trading site";
				status obsolete;
			}

			enum "trafficfactory" {
				opd:help "Traffic Factory provides an advertisement engine";
				status obsolete;
			}

			enum "trafficjunky" {
				opd:help "TrafficJunky is an online advertising service";
				status obsolete;
			}

			enum "transferbigfiles_com" {
				opd:help "Classifies web browsing on the transferbigfiles.com Direct DownLoad links service";
				status obsolete;
			}

			enum "travbuddy" {
				opd:help "This classifies the HTTP and SSL traffic to the host travbuddy.com";
				status obsolete;
			}

			enum "travellerspoint" {
				opd:help "This classifies the HTTP traffic to the host travellerspoint.com";
				status obsolete;
			}

			enum "travelocity" {
				opd:help "This classifies the HTTP traffic to the host travelocity.com";
				status obsolete;
			}

			enum "travian" {
				opd:help "This classifies the HTTP and SSL traffic to the host travian.co.id";
				status obsolete;
			}

			enum "trend" {
				opd:help "Azerbaijani news portal";
				status obsolete;
			}

			enum "trendmicro_update" {
				opd:help "Trendmicro_update is the protocol used for trendmicro software updates";
				status obsolete;
			}

			enum "tribe" {
				opd:help "This classifies the HTTP traffic to the host tribe.net";
				status obsolete;
			}

			enum "tribunnews" {
				opd:help "This classifies the HTTP and SSL traffic to the host tribunnews.com";
				status obsolete;
			}

			enum "trinidadexpress" {
				opd:help "Trinidadian news portal";
				status obsolete;
			}

			enum "trinituner" {
				opd:help "Automotive publications and community website in Trinidad and Tobago";
				status obsolete;
			}

			enum "trippy" {
				opd:help "Trippy is a social network where users share questions and answers about destinations they have visited around the globe";
				status obsolete;
			}

			enum "trombi" {
				opd:help "This classifies the HTTP traffic to the host trombi.com";
				status obsolete;
			}

			enum "trunk_1" {
				opd:help "The trunk_1 protocol (Trunk 1) is found over the IP layer (IANA protocol number: 23)";
				status obsolete;
			}

			enum "trunk_2" {
				opd:help "The trunk_2 protocol (Trunk 2) is found over the IP layer (IANA protocol number: 24)";
				status obsolete;
			}

			enum "truste" {
				opd:help "TRUSTe is a online privacy management services provider offering a broad suite of consumer, advertising, mobile, cloud and data privacy solutions";
				status obsolete;
			}

			enum "ts" {
				opd:help "Kyrgystani video streaming website";
				status obsolete;
			}

			enum "ttp" {
				opd:help "(Deprecated) The ttp protocol (TTP) is found over the IP layer (IANA protocol number: 84)";
				status obsolete;
			}

			enum "tu" {
				opd:help "Online video streaming and sharing website";
				status obsolete;
			}

			enum "tube8" {
				opd:help "Tube8 is a popular adult video streaming website";
				status obsolete;
			}

			enum "tubemogul" {
				opd:help "Tubemogul is an independent advertising software platform";
				status obsolete;
			}

			enum "tuberel" {
				opd:help "Adult video website";
				status obsolete;
			}

			enum "tudou" {
				opd:help "This classifies the HTTP traffic to the hosts tudou.com and at-img4.tdimg.com";
				status obsolete;
			}

			enum "tuenti" {
				opd:help "This classifies the HTTP traffic to the host tuenti.com";
				status obsolete;
			}

			enum "tukif" {
				opd:help "French porn content website";
				status obsolete;
			}

			enum "tuko" {
				opd:help "Trending news, viral content, gossip and entertainment news from Kenya";
				status obsolete;
			}

			enum "tumblr" {
				opd:help "Tumblr is a social networking and microblogging platform allowing users to publish blog posts and multimedia content";
				status obsolete;
			}

			enum "tune" {
				opd:help "Pakistani multimedia and lifestyle website";
				status obsolete;
			}

			enum "tune_inc" {
				opd:help "Tune is an enterprise platform providing measurement to mobile marketers and their partners";
				status obsolete;
			}

			enum "tunein" {
				opd:help "TuneIn is an audio streaming platform which gives free access to radios and podcasts";
				status obsolete;
			}

			enum "tunewiki" {
				opd:help "Lyrics and photos sharing webservice, available in web and mobile-app versions";
				status obsolete;
			}

			enum "tunigate" {
				opd:help "News web portal in Tunisia";
				status obsolete;
			}

			enum "tunisia_sat" {
				opd:help "Tunisian forum hosting platform";
				status obsolete;
			}

			enum "turbo" {
				opd:help "Car classified ads site in Azerbaijan";
				status obsolete;
			}

			enum "turbobit" {
				opd:help "File hosting and sharing service";
				status obsolete;
			}

			enum "turn" {
				opd:help "Turn provides audience, campaign and analytics services";
				status obsolete;
			}

			enum "turner" {
				opd:help "Turner is a video streaming solution provider for audio/video content web services";
				status obsolete;
			}

			enum "tut" {
				opd:help "Belarusian internet portal";
				status obsolete;
			}

			enum "tv" {
				opd:help "This classifies the HTTP traffic to the host tv.com";
				status obsolete;
			}

			enum "tv2" {
				opd:help "Danish news portal";
				status obsolete;
			}

			enum "tv3" {
				opd:help "Lithuanian news portal";
				status obsolete;
			}

			enum "tv4play" {
				opd:help "TV4 Play is a video streaming website broadcasting content from the TV4 Swedish TV channel";
				status obsolete;
			}

			enum "tvants" {
				opd:help "TVAnts is a peer-to-peer TV software, using the BitTorrent peer-to-peer technology";
				status obsolete;
			}

			enum "tvcatchup" {
				opd:help "TVCatchup is an internet television service for viewing free-to-air UK channels";
				status obsolete;
			}

			enum "tvking" {
				opd:help "TvKing is an application which is able to get video stream lists from its own website and from other ones";
				status obsolete;
			}

			enum "tvm" {
				opd:help "TV channel webportal from Malta, featuring live streaming";
				status obsolete;
			}

			enum "tvn_noticias" {
				opd:help "Web portal of a news TV Channel in Panama";
				status obsolete;
			}

			enum "tvnet" {
				opd:help "Latvian news and content portal";
				status obsolete;
			}

			enum "tvuplayer" {
				opd:help "TVUPlayer is an application intended to watch TV in peer_to-peer";
				status obsolete;
			}

			enum "twipple" {
				opd:help "Japanese application for posting cute images on Twitter";
				status obsolete;
			}

			enum "twitch" {
				opd:help "Twitch.tv is a live video streaming service focused on video games";
				status obsolete;
			}

			enum "twitpic" {
				opd:help "Photo sharing web service dedicated to Twitter";
				status obsolete;
			}

			enum "twitter" {
				opd:help "Online microblogging service that enables its users to read and send text-based short messages";
				status obsolete;
			}

			enum "twoo" {
				opd:help "Twoo is a social networking website, enabling users to connect to relatives, friends, or unknown people";
				status obsolete;
			}

			enum "txxx" {
				opd:help "Adult video website";
				status obsolete;
			}

			enum "uaudp" {
				opd:help "Telephony protocol by Alcatel-Lucent Enterprise which signals media flows and other control messages for the phones";
				status obsolete;
			}

			enum "uaudp_rtp" {
				opd:help "RTP media flow originated from a UA/UDP (Alcatel-Lucent Enterprise signaling protocol) session";
				status obsolete;
			}

			enum "uber" {
				opd:help "Uber is an American online transportation network company which connects smartphone consumers looking for a trip with drivers";
				status obsolete;
			}

			enum "ubuntu" {
				opd:help "Ubuntu is an open source software platform";
				status obsolete;
			}

			enum "ubuntu_one" {
				opd:help "(Deprecated) Ubuntu One is a cloud file storage service available on PC and smartphones";
				status obsolete;
			}

			enum "ucoz" {
				opd:help "uCoz is a free web hosting with a built-in content management system";
				status obsolete;
			}

			enum "ucp" {
				opd:help "Universal Computer Protocol is used by some mobile phones to send SMS";
				status obsolete;
			}

			enum "udn" {
				opd:help "Taiwan news site";
				status obsolete;
			}

			enum "udplite" {
				opd:help "The udplite protocol (Connectionless protocol very similar to UDP) is found over the IP layer (IANA protocol number: 136)";
				status obsolete;
			}

			enum "ukr" {
				opd:help "Ukrainian portal for news, media and lifestyle";
				status obsolete;
			}

			enum "ukwezi" {
				opd:help "Popular news website in Rwanda";
				status obsolete;
			}

			enum "ulp" {
				opd:help "User-plane Location Protocol (ULP) is used for data exchange as part of Assisted GPS";
				status obsolete;
			}

			enum "ultimahora" {
				opd:help "Honduran news portal";
				status obsolete;
			}

			enum "ultrashare_net" {
				opd:help "Classifies web browsing on the ultrashare.net Direct DownLoad links service";
				status obsolete;
			}

			enum "ultrasurf" {
				opd:help "Ultrasurf is a tunneling protocol used by the Ultrasurf software for Windows";
				status obsolete;
			}

			enum "umac" {
				opd:help "Web portal of the University of Macau";
				status obsolete;
			}

			enum "umeng" {
				opd:help "Umeng is providing mobile app analytics solutions for mobile development teams and individual developers";
				status obsolete;
			}

			enum "umuryango" {
				opd:help "News portal in Rwanda";
				status obsolete;
			}

			enum "umuseke" {
				opd:help "News and media webportal in Rwanda";
				status obsolete;
			}

			enum "unamexico" {
				opd:help "Web portal of a major university in Mexico";
				status obsolete;
			}

			enum "unamibia" {
				opd:help "Web portal of a major university in Namibia";
				status obsolete;
			}

			enum "unassigned_ip_prot_143" {
				opd:help "(Deprecated) The unassigned_ip_prot_143 protocol (IANA Unassigned Internet Protocol Number 143) is found over the IP layer (IANA protocol number: 143)";
				status obsolete;
			}

			enum "unassigned_ip_prot_144" {
				opd:help "(Deprecated) The unassigned_ip_prot_144 protocol (IANA Unassigned Internet Protocol Number 144) is found over the IP layer (IANA protocol number: 144)";
				status obsolete;
			}

			enum "unassigned_ip_prot_145" {
				opd:help "(Deprecated) The unassigned_ip_prot_145 protocol (IANA Unassigned Internet Protocol Number 145) is found over the IP layer (IANA protocol number: 145)";
				status obsolete;
			}

			enum "unassigned_ip_prot_146" {
				opd:help "(Deprecated) The unassigned_ip_prot_146 protocol (IANA Unassigned Internet Protocol Number 146) is found over the IP layer (IANA protocol number: 146)";
				status obsolete;
			}

			enum "unassigned_ip_prot_147" {
				opd:help "(Deprecated) The unassigned_ip_prot_147 protocol (IANA Unassigned Internet Protocol Number 147) is found over the IP layer (IANA protocol number: 147)";
				status obsolete;
			}

			enum "unassigned_ip_prot_148" {
				opd:help "(Deprecated) The unassigned_ip_prot_148 protocol (IANA Unassigned Internet Protocol Number 148) is found over the IP layer (IANA protocol number: 148)";
				status obsolete;
			}

			enum "unassigned_ip_prot_149" {
				opd:help "(Deprecated) The unassigned_ip_prot_149 protocol (IANA Unassigned Internet Protocol Number 149) is found over the IP layer (IANA protocol number: 149)";
				status obsolete;
			}

			enum "unassigned_ip_prot_150" {
				opd:help "(Deprecated) The unassigned_ip_prot_150 protocol (IANA Unassigned Internet Protocol Number 150) is found over the IP layer (IANA protocol number: 150)";
				status obsolete;
			}

			enum "unassigned_ip_prot_151" {
				opd:help "(Deprecated) The unassigned_ip_prot_151 protocol (IANA Unassigned Internet Protocol Number 151) is found over the IP layer (IANA protocol number: 151)";
				status obsolete;
			}

			enum "unassigned_ip_prot_152" {
				opd:help "(Deprecated) The unassigned_ip_prot_152 protocol (IANA Unassigned Internet Protocol Number 152) is found over the IP layer (IANA protocol number: 152)";
				status obsolete;
			}

			enum "unassigned_ip_prot_153" {
				opd:help "(Deprecated) The unassigned_ip_prot_153 protocol (IANA Unassigned Internet Protocol Number 153) is found over the IP layer (IANA protocol number: 153)";
				status obsolete;
			}

			enum "unassigned_ip_prot_154" {
				opd:help "(Deprecated) The unassigned_ip_prot_154 protocol (IANA Unassigned Internet Protocol Number 154) is found over the IP layer (IANA protocol number: 154)";
				status obsolete;
			}

			enum "unassigned_ip_prot_155" {
				opd:help "(Deprecated) The unassigned_ip_prot_155 protocol (IANA Unassigned Internet Protocol Number 155) is found over the IP layer (IANA protocol number: 155)";
				status obsolete;
			}

			enum "unassigned_ip_prot_156" {
				opd:help "(Deprecated) The unassigned_ip_prot_156 protocol (IANA Unassigned Internet Protocol Number 156) is found over the IP layer (IANA protocol number: 156)";
				status obsolete;
			}

			enum "unassigned_ip_prot_157" {
				opd:help "(Deprecated) The unassigned_ip_prot_157 protocol (IANA Unassigned Internet Protocol Number 157) is found over the IP layer (IANA protocol number: 157)";
				status obsolete;
			}

			enum "unassigned_ip_prot_158" {
				opd:help "(Deprecated) The unassigned_ip_prot_158 protocol (IANA Unassigned Internet Protocol Number 158) is found over the IP layer (IANA protocol number: 158)";
				status obsolete;
			}

			enum "unassigned_ip_prot_159" {
				opd:help "(Deprecated) The unassigned_ip_prot_159 protocol (IANA Unassigned Internet Protocol Number 159) is found over the IP layer (IANA protocol number: 159)";
				status obsolete;
			}

			enum "unassigned_ip_prot_160" {
				opd:help "(Deprecated) The unassigned_ip_prot_160 protocol (IANA Unassigned Internet Protocol Number 160) is found over the IP layer (IANA protocol number: 160)";
				status obsolete;
			}

			enum "unassigned_ip_prot_161" {
				opd:help "(Deprecated) The unassigned_ip_prot_161 protocol (IANA Unassigned Internet Protocol Number 161) is found over the IP layer (IANA protocol number: 161)";
				status obsolete;
			}

			enum "unassigned_ip_prot_162" {
				opd:help "(Deprecated) The unassigned_ip_prot_162 protocol (IANA Unassigned Internet Protocol Number 162) is found over the IP layer (IANA protocol number: 162)";
				status obsolete;
			}

			enum "unassigned_ip_prot_163" {
				opd:help "(Deprecated) The unassigned_ip_prot_163 protocol (IANA Unassigned Internet Protocol Number 163) is found over the IP layer (IANA protocol number: 163)";
				status obsolete;
			}

			enum "unassigned_ip_prot_164" {
				opd:help "(Deprecated) The unassigned_ip_prot_164 protocol (IANA Unassigned Internet Protocol Number 164) is found over the IP layer (IANA protocol number: 164)";
				status obsolete;
			}

			enum "unassigned_ip_prot_165" {
				opd:help "(Deprecated) The unassigned_ip_prot_165 protocol (IANA Unassigned Internet Protocol Number 165) is found over the IP layer (IANA protocol number: 165)";
				status obsolete;
			}

			enum "unassigned_ip_prot_166" {
				opd:help "(Deprecated) The unassigned_ip_prot_166 protocol (IANA Unassigned Internet Protocol Number 166) is found over the IP layer (IANA protocol number: 166)";
				status obsolete;
			}

			enum "unassigned_ip_prot_167" {
				opd:help "(Deprecated) The unassigned_ip_prot_167 protocol (IANA Unassigned Internet Protocol Number 167) is found over the IP layer (IANA protocol number: 167)";
				status obsolete;
			}

			enum "unassigned_ip_prot_168" {
				opd:help "(Deprecated) The unassigned_ip_prot_168 protocol (IANA Unassigned Internet Protocol Number 168) is found over the IP layer (IANA protocol number: 168)";
				status obsolete;
			}

			enum "unassigned_ip_prot_169" {
				opd:help "(Deprecated) The unassigned_ip_prot_169 protocol (IANA Unassigned Internet Protocol Number 169) is found over the IP layer (IANA protocol number: 169)";
				status obsolete;
			}

			enum "unassigned_ip_prot_170" {
				opd:help "(Deprecated) The unassigned_ip_prot_170 protocol (IANA Unassigned Internet Protocol Number 170) is found over the IP layer (IANA protocol number: 170)";
				status obsolete;
			}

			enum "unassigned_ip_prot_171" {
				opd:help "(Deprecated) The unassigned_ip_prot_171 protocol (IANA Unassigned Internet Protocol Number 171) is found over the IP layer (IANA protocol number: 171)";
				status obsolete;
			}

			enum "unassigned_ip_prot_172" {
				opd:help "(Deprecated) The unassigned_ip_prot_172 protocol (IANA Unassigned Internet Protocol Number 172) is found over the IP layer (IANA protocol number: 172)";
				status obsolete;
			}

			enum "unassigned_ip_prot_173" {
				opd:help "(Deprecated) The unassigned_ip_prot_173 protocol (IANA Unassigned Internet Protocol Number 173) is found over the IP layer (IANA protocol number: 173)";
				status obsolete;
			}

			enum "unassigned_ip_prot_174" {
				opd:help "(Deprecated) The unassigned_ip_prot_174 protocol (IANA Unassigned Internet Protocol Number 174) is found over the IP layer (IANA protocol number: 174)";
				status obsolete;
			}

			enum "unassigned_ip_prot_175" {
				opd:help "(Deprecated) The unassigned_ip_prot_175 protocol (IANA Unassigned Internet Protocol Number 175) is found over the IP layer (IANA protocol number: 175)";
				status obsolete;
			}

			enum "unassigned_ip_prot_176" {
				opd:help "(Deprecated) The unassigned_ip_prot_176 protocol (IANA Unassigned Internet Protocol Number 176) is found over the IP layer (IANA protocol number: 176)";
				status obsolete;
			}

			enum "unassigned_ip_prot_177" {
				opd:help "(Deprecated) The unassigned_ip_prot_177 protocol (IANA Unassigned Internet Protocol Number 177) is found over the IP layer (IANA protocol number: 177)";
				status obsolete;
			}

			enum "unassigned_ip_prot_178" {
				opd:help "(Deprecated) The unassigned_ip_prot_178 protocol (IANA Unassigned Internet Protocol Number 178) is found over the IP layer (IANA protocol number: 178)";
				status obsolete;
			}

			enum "unassigned_ip_prot_179" {
				opd:help "(Deprecated) The unassigned_ip_prot_179 protocol (IANA Unassigned Internet Protocol Number 179) is found over the IP layer (IANA protocol number: 179)";
				status obsolete;
			}

			enum "unassigned_ip_prot_180" {
				opd:help "(Deprecated) The unassigned_ip_prot_180 protocol (IANA Unassigned Internet Protocol Number 180) is found over the IP layer (IANA protocol number: 180)";
				status obsolete;
			}

			enum "unassigned_ip_prot_181" {
				opd:help "(Deprecated) The unassigned_ip_prot_181 protocol (IANA Unassigned Internet Protocol Number 181) is found over the IP layer (IANA protocol number: 181)";
				status obsolete;
			}

			enum "unassigned_ip_prot_182" {
				opd:help "(Deprecated) The unassigned_ip_prot_182 protocol (IANA Unassigned Internet Protocol Number 182) is found over the IP layer (IANA protocol number: 182)";
				status obsolete;
			}

			enum "unassigned_ip_prot_183" {
				opd:help "(Deprecated) The unassigned_ip_prot_183 protocol (IANA Unassigned Internet Protocol Number 183) is found over the IP layer (IANA protocol number: 183)";
				status obsolete;
			}

			enum "unassigned_ip_prot_184" {
				opd:help "(Deprecated) The unassigned_ip_prot_184 protocol (IANA Unassigned Internet Protocol Number 184) is found over the IP layer (IANA protocol number: 184)";
				status obsolete;
			}

			enum "unassigned_ip_prot_185" {
				opd:help "(Deprecated) The unassigned_ip_prot_185 protocol (IANA Unassigned Internet Protocol Number 185) is found over the IP layer (IANA protocol number: 185)";
				status obsolete;
			}

			enum "unassigned_ip_prot_186" {
				opd:help "(Deprecated) The unassigned_ip_prot_186 protocol (IANA Unassigned Internet Protocol Number 186) is found over the IP layer (IANA protocol number: 186)";
				status obsolete;
			}

			enum "unassigned_ip_prot_187" {
				opd:help "(Deprecated) The unassigned_ip_prot_187 protocol (IANA Unassigned Internet Protocol Number 187) is found over the IP layer (IANA protocol number: 187)";
				status obsolete;
			}

			enum "unassigned_ip_prot_188" {
				opd:help "(Deprecated) The unassigned_ip_prot_188 protocol (IANA Unassigned Internet Protocol Number 188) is found over the IP layer (IANA protocol number: 188)";
				status obsolete;
			}

			enum "unassigned_ip_prot_189" {
				opd:help "(Deprecated) The unassigned_ip_prot_189 protocol (IANA Unassigned Internet Protocol Number 189) is found over the IP layer (IANA protocol number: 189)";
				status obsolete;
			}

			enum "unassigned_ip_prot_190" {
				opd:help "(Deprecated) The unassigned_ip_prot_190 protocol (IANA Unassigned Internet Protocol Number 190) is found over the IP layer (IANA protocol number: 190)";
				status obsolete;
			}

			enum "unassigned_ip_prot_191" {
				opd:help "(Deprecated) The unassigned_ip_prot_191 protocol (IANA Unassigned Internet Protocol Number 191) is found over the IP layer (IANA protocol number: 191)";
				status obsolete;
			}

			enum "unassigned_ip_prot_192" {
				opd:help "(Deprecated) The unassigned_ip_prot_192 protocol (IANA Unassigned Internet Protocol Number 192) is found over the IP layer (IANA protocol number: 192)";
				status obsolete;
			}

			enum "unassigned_ip_prot_193" {
				opd:help "(Deprecated) The unassigned_ip_prot_193 protocol (IANA Unassigned Internet Protocol Number 193) is found over the IP layer (IANA protocol number: 193)";
				status obsolete;
			}

			enum "unassigned_ip_prot_194" {
				opd:help "(Deprecated) The unassigned_ip_prot_194 protocol (IANA Unassigned Internet Protocol Number 194) is found over the IP layer (IANA protocol number: 194)";
				status obsolete;
			}

			enum "unassigned_ip_prot_195" {
				opd:help "(Deprecated) The unassigned_ip_prot_195 protocol (IANA Unassigned Internet Protocol Number 195) is found over the IP layer (IANA protocol number: 195)";
				status obsolete;
			}

			enum "unassigned_ip_prot_196" {
				opd:help "(Deprecated) The unassigned_ip_prot_196 protocol (IANA Unassigned Internet Protocol Number 196) is found over the IP layer (IANA protocol number: 196)";
				status obsolete;
			}

			enum "unassigned_ip_prot_197" {
				opd:help "(Deprecated) The unassigned_ip_prot_197 protocol (IANA Unassigned Internet Protocol Number 197) is found over the IP layer (IANA protocol number: 197)";
				status obsolete;
			}

			enum "unassigned_ip_prot_198" {
				opd:help "(Deprecated) The unassigned_ip_prot_198 protocol (IANA Unassigned Internet Protocol Number 198) is found over the IP layer (IANA protocol number: 198)";
				status obsolete;
			}

			enum "unassigned_ip_prot_199" {
				opd:help "(Deprecated) The unassigned_ip_prot_199 protocol (IANA Unassigned Internet Protocol Number 199) is found over the IP layer (IANA protocol number: 199)";
				status obsolete;
			}

			enum "unassigned_ip_prot_200" {
				opd:help "(Deprecated) The unassigned_ip_prot_200 protocol (IANA Unassigned Internet Protocol Number 200) is found over the IP layer (IANA protocol number: 200)";
				status obsolete;
			}

			enum "unassigned_ip_prot_201" {
				opd:help "(Deprecated) The unassigned_ip_prot_201 protocol (IANA Unassigned Internet Protocol Number 201) is found over the IP layer (IANA protocol number: 201)";
				status obsolete;
			}

			enum "unassigned_ip_prot_202" {
				opd:help "(Deprecated) The unassigned_ip_prot_202 protocol (IANA Unassigned Internet Protocol Number 202) is found over the IP layer (IANA protocol number: 202)";
				status obsolete;
			}

			enum "unassigned_ip_prot_203" {
				opd:help "(Deprecated) The unassigned_ip_prot_203 protocol (IANA Unassigned Internet Protocol Number 203) is found over the IP layer (IANA protocol number: 203)";
				status obsolete;
			}

			enum "unassigned_ip_prot_204" {
				opd:help "(Deprecated) The unassigned_ip_prot_204 protocol (IANA Unassigned Internet Protocol Number 204) is found over the IP layer (IANA protocol number: 204)";
				status obsolete;
			}

			enum "unassigned_ip_prot_205" {
				opd:help "(Deprecated) The unassigned_ip_prot_205 protocol (IANA Unassigned Internet Protocol Number 205) is found over the IP layer (IANA protocol number: 205)";
				status obsolete;
			}

			enum "unassigned_ip_prot_206" {
				opd:help "(Deprecated) The unassigned_ip_prot_206 protocol (IANA Unassigned Internet Protocol Number 206) is found over the IP layer (IANA protocol number: 206)";
				status obsolete;
			}

			enum "unassigned_ip_prot_207" {
				opd:help "(Deprecated) The unassigned_ip_prot_207 protocol (IANA Unassigned Internet Protocol Number 207) is found over the IP layer (IANA protocol number: 207)";
				status obsolete;
			}

			enum "unassigned_ip_prot_208" {
				opd:help "(Deprecated) The unassigned_ip_prot_208 protocol (IANA Unassigned Internet Protocol Number 208) is found over the IP layer (IANA protocol number: 208)";
				status obsolete;
			}

			enum "unassigned_ip_prot_209" {
				opd:help "(Deprecated) The unassigned_ip_prot_209 protocol (IANA Unassigned Internet Protocol Number 209) is found over the IP layer (IANA protocol number: 209)";
				status obsolete;
			}

			enum "unassigned_ip_prot_210" {
				opd:help "(Deprecated) The unassigned_ip_prot_210 protocol (IANA Unassigned Internet Protocol Number 210) is found over the IP layer (IANA protocol number: 210)";
				status obsolete;
			}

			enum "unassigned_ip_prot_211" {
				opd:help "(Deprecated) The unassigned_ip_prot_211 protocol (IANA Unassigned Internet Protocol Number 211) is found over the IP layer (IANA protocol number: 211)";
				status obsolete;
			}

			enum "unassigned_ip_prot_212" {
				opd:help "(Deprecated) The unassigned_ip_prot_212 protocol (IANA Unassigned Internet Protocol Number 212) is found over the IP layer (IANA protocol number: 212)";
				status obsolete;
			}

			enum "unassigned_ip_prot_213" {
				opd:help "(Deprecated) The unassigned_ip_prot_213 protocol (IANA Unassigned Internet Protocol Number 213) is found over the IP layer (IANA protocol number: 213)";
				status obsolete;
			}

			enum "unassigned_ip_prot_214" {
				opd:help "(Deprecated) The unassigned_ip_prot_214 protocol (IANA Unassigned Internet Protocol Number 214) is found over the IP layer (IANA protocol number: 214)";
				status obsolete;
			}

			enum "unassigned_ip_prot_215" {
				opd:help "(Deprecated) The unassigned_ip_prot_215 protocol (IANA Unassigned Internet Protocol Number 215) is found over the IP layer (IANA protocol number: 215)";
				status obsolete;
			}

			enum "unassigned_ip_prot_216" {
				opd:help "(Deprecated) The unassigned_ip_prot_216 protocol (IANA Unassigned Internet Protocol Number 216) is found over the IP layer (IANA protocol number: 216)";
				status obsolete;
			}

			enum "unassigned_ip_prot_217" {
				opd:help "(Deprecated) The unassigned_ip_prot_217 protocol (IANA Unassigned Internet Protocol Number 217) is found over the IP layer (IANA protocol number: 217)";
				status obsolete;
			}

			enum "unassigned_ip_prot_218" {
				opd:help "(Deprecated) The unassigned_ip_prot_218 protocol (IANA Unassigned Internet Protocol Number 218) is found over the IP layer (IANA protocol number: 218)";
				status obsolete;
			}

			enum "unassigned_ip_prot_219" {
				opd:help "(Deprecated) The unassigned_ip_prot_219 protocol (IANA Unassigned Internet Protocol Number 219) is found over the IP layer (IANA protocol number: 219)";
				status obsolete;
			}

			enum "unassigned_ip_prot_220" {
				opd:help "(Deprecated) The unassigned_ip_prot_220 protocol (IANA Unassigned Internet Protocol Number 220) is found over the IP layer (IANA protocol number: 220)";
				status obsolete;
			}

			enum "unassigned_ip_prot_221" {
				opd:help "(Deprecated) The unassigned_ip_prot_221 protocol (IANA Unassigned Internet Protocol Number 221) is found over the IP layer (IANA protocol number: 221)";
				status obsolete;
			}

			enum "unassigned_ip_prot_222" {
				opd:help "(Deprecated) The unassigned_ip_prot_222 protocol (IANA Unassigned Internet Protocol Number 222) is found over the IP layer (IANA protocol number: 222)";
				status obsolete;
			}

			enum "unassigned_ip_prot_223" {
				opd:help "(Deprecated) The unassigned_ip_prot_223 protocol (IANA Unassigned Internet Protocol Number 223) is found over the IP layer (IANA protocol number: 223)";
				status obsolete;
			}

			enum "unassigned_ip_prot_224" {
				opd:help "(Deprecated) The unassigned_ip_prot_224 protocol (IANA Unassigned Internet Protocol Number 224) is found over the IP layer (IANA protocol number: 224)";
				status obsolete;
			}

			enum "unassigned_ip_prot_225" {
				opd:help "(Deprecated) The unassigned_ip_prot_225 protocol (IANA Unassigned Internet Protocol Number 225) is found over the IP layer (IANA protocol number: 225)";
				status obsolete;
			}

			enum "unassigned_ip_prot_226" {
				opd:help "(Deprecated) The unassigned_ip_prot_226 protocol (IANA Unassigned Internet Protocol Number 226) is found over the IP layer (IANA protocol number: 226)";
				status obsolete;
			}

			enum "unassigned_ip_prot_227" {
				opd:help "(Deprecated) The unassigned_ip_prot_227 protocol (IANA Unassigned Internet Protocol Number 227) is found over the IP layer (IANA protocol number: 227)";
				status obsolete;
			}

			enum "unassigned_ip_prot_228" {
				opd:help "(Deprecated) The unassigned_ip_prot_228 protocol (IANA Unassigned Internet Protocol Number 228) is found over the IP layer (IANA protocol number: 228)";
				status obsolete;
			}

			enum "unassigned_ip_prot_229" {
				opd:help "(Deprecated) The unassigned_ip_prot_229 protocol (IANA Unassigned Internet Protocol Number 229) is found over the IP layer (IANA protocol number: 229)";
				status obsolete;
			}

			enum "unassigned_ip_prot_230" {
				opd:help "(Deprecated) The unassigned_ip_prot_230 protocol (IANA Unassigned Internet Protocol Number 230) is found over the IP layer (IANA protocol number: 230)";
				status obsolete;
			}

			enum "unassigned_ip_prot_231" {
				opd:help "(Deprecated) The unassigned_ip_prot_231 protocol (IANA Unassigned Internet Protocol Number 231) is found over the IP layer (IANA protocol number: 231)";
				status obsolete;
			}

			enum "unassigned_ip_prot_232" {
				opd:help "(Deprecated) The unassigned_ip_prot_232 protocol (IANA Unassigned Internet Protocol Number 232) is found over the IP layer (IANA protocol number: 232)";
				status obsolete;
			}

			enum "unassigned_ip_prot_233" {
				opd:help "(Deprecated) The unassigned_ip_prot_233 protocol (IANA Unassigned Internet Protocol Number 233) is found over the IP layer (IANA protocol number: 233)";
				status obsolete;
			}

			enum "unassigned_ip_prot_234" {
				opd:help "(Deprecated) The unassigned_ip_prot_234 protocol (IANA Unassigned Internet Protocol Number 234) is found over the IP layer (IANA protocol number: 234)";
				status obsolete;
			}

			enum "unassigned_ip_prot_235" {
				opd:help "(Deprecated) The unassigned_ip_prot_235 protocol (IANA Unassigned Internet Protocol Number 235) is found over the IP layer (IANA protocol number: 235)";
				status obsolete;
			}

			enum "unassigned_ip_prot_236" {
				opd:help "(Deprecated) The unassigned_ip_prot_236 protocol (IANA Unassigned Internet Protocol Number 236) is found over the IP layer (IANA protocol number: 236)";
				status obsolete;
			}

			enum "unassigned_ip_prot_237" {
				opd:help "(Deprecated) The unassigned_ip_prot_237 protocol (IANA Unassigned Internet Protocol Number 237) is found over the IP layer (IANA protocol number: 237)";
				status obsolete;
			}

			enum "unassigned_ip_prot_238" {
				opd:help "(Deprecated) The unassigned_ip_prot_238 protocol (IANA Unassigned Internet Protocol Number 238) is found over the IP layer (IANA protocol number: 238)";
				status obsolete;
			}

			enum "unassigned_ip_prot_239" {
				opd:help "(Deprecated) The unassigned_ip_prot_239 protocol (IANA Unassigned Internet Protocol Number 239) is found over the IP layer (IANA protocol number: 239)";
				status obsolete;
			}

			enum "unassigned_ip_prot_240" {
				opd:help "(Deprecated) The unassigned_ip_prot_240 protocol (IANA Unassigned Internet Protocol Number 240) is found over the IP layer (IANA protocol number: 240)";
				status obsolete;
			}

			enum "unassigned_ip_prot_241" {
				opd:help "(Deprecated) The unassigned_ip_prot_241 protocol (IANA Unassigned Internet Protocol Number 241) is found over the IP layer (IANA protocol number: 241)";
				status obsolete;
			}

			enum "unassigned_ip_prot_242" {
				opd:help "(Deprecated) The unassigned_ip_prot_242 protocol (IANA Unassigned Internet Protocol Number 242) is found over the IP layer (IANA protocol number: 242)";
				status obsolete;
			}

			enum "unassigned_ip_prot_243" {
				opd:help "(Deprecated) The unassigned_ip_prot_243 protocol (IANA Unassigned Internet Protocol Number 243) is found over the IP layer (IANA protocol number: 243)";
				status obsolete;
			}

			enum "unassigned_ip_prot_244" {
				opd:help "(Deprecated) The unassigned_ip_prot_244 protocol (IANA Unassigned Internet Protocol Number 244) is found over the IP layer (IANA protocol number: 244)";
				status obsolete;
			}

			enum "unassigned_ip_prot_245" {
				opd:help "(Deprecated) The unassigned_ip_prot_245 protocol (IANA Unassigned Internet Protocol Number 245) is found over the IP layer (IANA protocol number: 245)";
				status obsolete;
			}

			enum "unassigned_ip_prot_246" {
				opd:help "(Deprecated) The unassigned_ip_prot_246 protocol (IANA Unassigned Internet Protocol Number 246) is found over the IP layer (IANA protocol number: 246)";
				status obsolete;
			}

			enum "unassigned_ip_prot_247" {
				opd:help "(Deprecated) The unassigned_ip_prot_247 protocol (IANA Unassigned Internet Protocol Number 247) is found over the IP layer (IANA protocol number: 247)";
				status obsolete;
			}

			enum "unassigned_ip_prot_248" {
				opd:help "(Deprecated) The unassigned_ip_prot_248 protocol (IANA Unassigned Internet Protocol Number 248) is found over the IP layer (IANA protocol number: 248)";
				status obsolete;
			}

			enum "unassigned_ip_prot_249" {
				opd:help "(Deprecated) The unassigned_ip_prot_249 protocol (IANA Unassigned Internet Protocol Number 249) is found over the IP layer (IANA protocol number: 249)";
				status obsolete;
			}

			enum "unassigned_ip_prot_250" {
				opd:help "(Deprecated) The unassigned_ip_prot_250 protocol (IANA Unassigned Internet Protocol Number 250) is found over the IP layer (IANA protocol number: 250)";
				status obsolete;
			}

			enum "unassigned_ip_prot_251" {
				opd:help "(Deprecated) The unassigned_ip_prot_251 protocol (IANA Unassigned Internet Protocol Number 251) is found over the IP layer (IANA protocol number: 251)";
				status obsolete;
			}

			enum "unassigned_ip_prot_252" {
				opd:help "(Deprecated) The unassigned_ip_prot_252 protocol (IANA Unassigned Internet Protocol Number 252) is found over the IP layer (IANA protocol number: 252)";
				status obsolete;
			}

			enum "unegui" {
				opd:help "Classified ads web service in Mongolia";
				status obsolete;
			}

			enum "universiti_brunei_darussalam" {
				opd:help "Website of a major university in Brunei";
				status obsolete;
			}

			enum "university_of_botswana" {
				opd:help "Web portal of the University of Botswana";
				status obsolete;
			}

			enum "univision" {
				opd:help "This classifies the HTTP and SSL traffic to the host univision.com";
				status obsolete;
			}

			enum "unknown" {
				opd:help "Unknown is a virtual protocol created for DPI that represents flows that are not recognized by the system";
				status obsolete;
			}

			enum "unruly" {
				opd:help "Unruly is an advertisement technology company that gets videos watched, tracked and shared across the Open Web";
				status obsolete;
			}

			enum "uol" {
				opd:help "Brazilian news portal";
				status obsolete;
			}

			enum "upload_com" {
				opd:help "Classifies web browsing on the CNET upload.com Direct DownLoad links service";
				status obsolete;
			}

			enum "uploaded_net" {
				opd:help "Classifies web browsing on the uploaded.net Direct DownLoad links service";
				status obsolete;
			}

			enum "uploading" {
				opd:help "Secured file hosting and sharing web service with ability to upload from different desktop and mobile platforms";
				status obsolete;
			}

			enum "uploadingit_com" {
				opd:help "(Deprecated) Classifies web browsing on the uploadingit.com Direct DownLoad links service";
				status obsolete;
			}

			enum "uplynk" {
				opd:help "upLynk is an easy way to stream your live and on demand video to all devices and platforms";
				status obsolete;
			}

			enum "uptobox" {
				opd:help "File hosting web service for sharing files up to 1024MB each";
				status obsolete;
			}

			enum "uptodown" {
				opd:help "Multiplatform and non restrictive app store for mobile devices";
				status obsolete;
			}

			enum "urbanairship" {
				opd:help "Urbanairship provides tools and services designed for mobile application developers";
				status obsolete;
			}

			enum "urdupoint" {
				opd:help "Pakistani news portal";
				status obsolete;
			}

			enum "usabit_com" {
				opd:help "BitTorrent tracker search engine";
				status obsolete;
			}

			enum "usatoday" {
				opd:help "This classifies the HTTP traffic to the host usatoday.com";
				status obsolete;
			}

			enum "usbmux" {
				opd:help "iTunes communicates with the iPhone using usbmux";
				status obsolete;
			}

			enum "usejump" {
				opd:help "This classifies the HTTP traffic to the host usejump.com";
				status obsolete;
			}

			enum "usp" {
				opd:help "Website of the University of the South Pacific";
				status obsolete;
			}

			enum "ustream" {
				opd:help "Ustream is a live video broadcasting webservice available on PC and mobile platforms";
				status obsolete;
			}

			enum "uti" {
				opd:help "The uti protocol (UTI) is found over the IP layer (IANA protocol number: 120)";
				status obsolete;
			}

			enum "utorrent" {
				opd:help "uTorrent is a closed source BitTorrent client";
				status obsolete;
			}

			enum "utp" {
				opd:help "BitTorrent transport layer";
				status obsolete;
			}

			enum "uusee" {
				opd:help "Uusee is a peer-to-peer TV software, using the BitTorrent peer-to-peer technology";
				status obsolete;
			}

			enum "uwi" {
				opd:help "Web portal of the University of The West Indies";
				status obsolete;
			}

			enum "uz_ac" {
				opd:help "General information, student directory, and links to internal resources of the University of Zimbabwe";
				status obsolete;
			}

			enum "v5ua" {
				opd:help "V5UA is a transport mechanism for V5.2 messages in an IP network, through SCTP";
				status obsolete;
			}

			enum "vaguthu" {
				opd:help "Maldivian news website";
				status obsolete;
			}

			enum "vakaka" {
				opd:help "This classifies the HTTP traffic to the host vakaka.com";
				status obsolete;
			}

			enum "vampirefreaks" {
				opd:help "This classifies the HTTP traffic to the host vampirefreaks.com";
				status obsolete;
			}

			enum "vanguardngr" {
				opd:help "Nigerian news portal";
				status obsolete;
			}

			enum "varzesh3" {
				opd:help "Persian online sports new portal";
				status obsolete;
			}

			enum "vbox7" {
				opd:help "Bulgarian video streaming website";
				status obsolete;
			}

			enum "vecer" {
				opd:help "Macedonian and Balkan news portal";
				status obsolete;
			}

			enum "vecernji" {
				opd:help "Croatian news portal";
				status obsolete;
			}

			enum "vector" {
				opd:help "BitTorrent tracker search engine";
				status obsolete;
			}

			enum "veetle" {
				opd:help "This classifies the HTTP traffic to the host veetle.com";
				status obsolete;
			}

			enum "veohtv" {
				opd:help "VeohTV is a VOD streaming service which includes both client software and a website with embedded flash videos";
				status obsolete;
			}

			enum "verizon" {
				opd:help "Verizon Internet provider hosts and services";
				status obsolete;
			}

			enum "vertamedia" {
				opd:help "(Deprecated) VertaMedia is a Supply-Side Platform with its own Video Ad Marketplace";
				status obsolete;
			}

			enum "vestniktm" {
				opd:help "Classified ads website in Turkmenistan";
				status obsolete;
			}

			enum "vetogate" {
				opd:help "Egyptian news portal";
				status obsolete;
			}

			enum "vevo" {
				opd:help "VEVO is a music video streaming platform sponsored by Google, Universal Music Group and Sony Music Entertainment";
				status obsolete;
			}

			enum "vg" {
				opd:help "Norwegian news portal";
				status obsolete;
			}

			enum "viadeo" {
				opd:help "Viadeo is a website designed to manage professional contacts";
				status obsolete;
			}

			enum "viaplay" {
				opd:help "Viaplay is a video-on-demand service for the Nordic countries, which uses Silverlight to stream videos";
				status obsolete;
			}

			enum "viber" {
				opd:help "Viber is a free embedded voice over-ip application, for smartphones";
				status obsolete;
			}

			enum "videobash" {
				opd:help "This classifies the HTTP traffic to the host videobash.com";
				status obsolete;
			}

			enum "videojug" {
				opd:help "Videojug is an owner of various online consumer TV channels";
				status obsolete;
			}

			enum "videoplaza" {
				opd:help "Videoplaza provides tools to broadcasters, publishers and networks to maximise their advert revenues from their video content";
				status obsolete;
			}

			enum "videosurf" {
				opd:help "This classifies the HTTP traffic to the host videosurf.com";
				status obsolete;
			}

			enum "videosz" {
				opd:help "Porn content website";
				status obsolete;
			}

			enum "vidmax" {
				opd:help "Website for streaming funny, fail, punk and war videos";
				status obsolete;
			}

			enum "vidme" {
				opd:help "User video content website";
				status obsolete;
			}

			enum "vidyard" {
				opd:help "Vidyard is a video marketing platform";
				status obsolete;
			}

			enum "vietbao" {
				opd:help "This classifies the HTTP traffic to the host vietbao.vn";
				status obsolete;
			}

			enum "viewpath" {
				opd:help "Viewpath is an online project management and collaboration tool";
				status obsolete;
			}

			enum "viewster" {
				opd:help "Viewster delivers free video";
				status obsolete;
			}

			enum "vijesti" {
				opd:help "Serbian news portal";
				status obsolete;
			}

			enum "vimeo" {
				opd:help "Vimeo is a high definition video streaming platform, to be accessed from a web browser or mobile applications";
				status obsolete;
			}

			enum "vine" {
				opd:help "Vine is a short-form video sharing service";
				status obsolete;
			}

			enum "vines" {
				opd:help "Vines is a network layer protocol, enabling the routing of packets from the transport layer from one node to the transport layer in another node";
				status obsolete;
			}

			enum "visa" {
				opd:help "The visa protocol (VISA Protocol) is found over the IP layer (IANA protocol number: 70)";
				status obsolete;
			}

			enum "visa_checkout" {
				opd:help "Visa Checkout provides a single sign-in service to pay for online shopping purchases";
				status obsolete;
			}

			enum "visadd" {
				opd:help "VisAdd provides advertisement services (refers to a malware)";
				status obsolete;
			}

			enum "visir" {
				opd:help "Icelandic news portal";
				status obsolete;
			}

			enum "vivanews" {
				opd:help "This classifies the HTTP traffic to the hosts vivanews.com and viva.co.id";
				status obsolete;
			}

			enum "vjc_comp" {
				opd:help "Van Jacobson TCP/IP Header Compression is a data compression protocol described in RFC 1144, specifically designed by Van Jacobson to improve TCP/IP performance";
				status obsolete;
			}

			enum "vjc_uncomp" {
				opd:help "Van Jacobson TCP/IP Header Compression is a data compression protocol described in RFC 1144, specifically designed by Van Jacobson to improve TCP/IP performance";
				status obsolete;
			}

			enum "vkontakte" {
				opd:help "vkontakte is a European social network service popular among Russian-Speaking users";
				status obsolete;
			}

			enum "vmotion" {
				opd:help "vMotion is the VMware protocol which allows hot migration of virtual machines between different vSphere servers running on different hosts";
				status obsolete;
			}

			enum "vmtp" {
				opd:help "The vmtp protocol (VMTP) is found over the IP layer (IANA protocol number: 81)";
				status obsolete;
			}

			enum "vmware" {
				opd:help "VMWare is a protocol used by the VMWare application, allowing it to have network interfaces and remote access to a virtual machine";
				status obsolete;
			}

			enum "vmware_horizon_view" {
				opd:help "Vmware Horizon View is a commercial desktop-virtualization product developed by VMware";
				status obsolete;
			}

			enum "vnetip" {
				opd:help "Yokogawa's control communication network approved by international standards (IEC 61784-2 Ed.2.0)";
				status obsolete;
			}

			enum "vnexpress" {
				opd:help "Vietnamese news portal";
				status obsolete;
			}

			enum "voddler" {
				opd:help "Voddler is a streaming client application distributing movies and television programming using a patented hybrid peer-to-peer distribution system";
				status obsolete;
			}

			enum "vox" {
				opd:help "General news website";
				status obsolete;
			}

			enum "vpnoverdns" {
				opd:help "Vpnoverdns is a solution which provides tunneling through the standard DNS protocol";
				status obsolete;
			}

			enum "vrrp" {
				opd:help "Virtual Router Redundancy Protocol (VRRP) is a protocol designed to eliminate the single point of failure inherent in the static default routed environment";
				status obsolete;
			}

			enum "vsee" {
				opd:help "Vsee is a videoconferencing software";
				status obsolete;
			}

			enum "vtun" {
				opd:help "Software that creates virtual tunnels over TCP/IP networks";
				status obsolete;
			}

			enum "vtunnel" {
				opd:help "Vtunnel is a WEB proxy allowing the user to bypass firewalls and access restricted resources";
				status obsolete;
			}

			enum "vtv" {
				opd:help "News webportal of a Vietnamese TV and media group";
				status obsolete;
			}

			enum "vube" {
				opd:help "Monthly video contest and video sharing website";
				status obsolete;
			}

			enum "vuiviet" {
				opd:help "Vietnamese online entertainment portal";
				status obsolete;
			}

			enum "vuze" {
				opd:help "Vuze is a BitTorrent client";
				status obsolete;
			}

			enum "vyew" {
				opd:help "This classifies the HTTP traffic to the host vyew.com";
				status obsolete;
			}

			enum "vz_lt" {
				opd:help "Lithuanian business related news portal";
				status obsolete;
			}

			enum "wada" {
				opd:help "Vietnamese web search engine";
				status obsolete;
			}

			enum "wakoopa" {
				opd:help "This classifies the HTTP traffic to the host wakoopa.com";
				status obsolete;
			}

			enum "walla" {
				opd:help "Israeli internet portal";
				status obsolete;
			}

			enum "wallstreetjournal_china" {
				opd:help "Chinese version of the Wall Street Journal";
				status obsolete;
			}

			enum "walmart" {
				opd:help "E-commerce website of the famous American retail chain";
				status obsolete;
			}

			enum "wamba" {
				opd:help "Dating portal website framework";
				status obsolete;
			}

			enum "wandoujia" {
				opd:help "Chinese mobile (Android applications)";
				status obsolete;
			}

			enum "wapa" {
				opd:help "Multimedia web portal of the WAPA-TV television station located in Puerto Rico";
				status obsolete;
			}

			enum "wasabi" {
				opd:help "This classifies the HTTP and SSL traffic to the host wasabi.com";
				status obsolete;
			}

			enum "washingtonpost" {
				opd:help "This classifies the HTTP and SSL traffic to the host washingtonpost.com";
				status obsolete;
			}

			enum "wat" {
				opd:help "This classifies the traffic to the host wat.tv";
				status obsolete;
			}

			enum "wattan" {
				opd:help "Palestinian multimedia news website";
				status obsolete;
			}

			enum "wayn" {
				opd:help "This classifies the HTTP traffic to the host wayn.com";
				status obsolete;
			}

			enum "waze" {
				opd:help "Waze is a community based mapping, traffic & navigation app";
				status obsolete;
			}

			enum "wb_expak" {
				opd:help "The wb_expak protocol (WIDEBAND EXPAK) is found over the IP layer (IANA protocol number: 79)";
				status obsolete;
			}

			enum "wb_mon" {
				opd:help "The wb_mon protocol (WIDEBAND Monitoring) is found over the IP layer (IANA protocol number: 78)";
				status obsolete;
			}

			enum "wccp" {
				opd:help "WCCP is a Cisco protocol that specifies interactions between one or more routers and one or more web-caches";
				status obsolete;
			}

			enum "weather" {
				opd:help "This classifies the HTTP traffic to the hosts weather.com and weather.com.cn";
				status obsolete;
			}

			enum "weather2umbrella" {
				opd:help "World Weather Forecast";
				status obsolete;
			}

			enum "weather4all" {
				opd:help "Macedonian weather forecast website";
				status obsolete;
			}

			enum "web" {
				opd:help "(Deprecated) Famous German web portal";
				status obsolete;
			}

			enum "web_crawler" {
				opd:help "This classifies the HTTP traffic to the host webcrawler.com";
				status obsolete;
			}

			enum "web_de" {
				opd:help "Famous German web portal";
				status obsolete;
			}

			enum "webbiographies" {
				opd:help "This classifies the HTTP traffic to the host webbiographies.com";
				status obsolete;
			}

			enum "webex" {
				opd:help "WebEx is an online meeting, videoconferencing and collaborative application";
				status obsolete;
			}

			enum "webex_weboffice" {
				opd:help "WebOffice is a collaboration suite for managing small businesses teams";
				status obsolete;
			}

			enum "weborama" {
				opd:help "Weborama is specialized in marketing data collection, and advertising campaigns online broadcasting";
				status obsolete;
			}

			enum "websocket" {
				opd:help "The WebSocket Protocol, as described in IETF RFC6455";
				status obsolete;
			}

			enum "webtretho" {
				opd:help "Vietnamese women's lifestyle website";
				status obsolete;
			}

			enum "wechat" {
				opd:help "WeChat is a text and voice messaging application for mobile";
				status obsolete;
			}

			enum "weiphone" {
				opd:help "Weiphone.com is a Chinese iPhone community";
				status obsolete;
			}

			enum "wellsfargo" {
				opd:help "Wells Fargo online banking web portal";
				status obsolete;
			}

			enum "weourfamily" {
				opd:help "This classifies the HTTP traffic to the host weourfamily.com";
				status obsolete;
			}

			enum "werkenntwen" {
				opd:help "This classifies the HTTP traffic to the host wer-kennt-wen.de";
				status obsolete;
			}

			enum "wesp" {
				opd:help "The wesp protocol (Wrapped Encapsulating Security Payload) is found over the IP layer (IANA protocol number: 141)";
				status obsolete;
			}

			enum "westpac" {
				opd:help "Australia s First Bank with a range of innovative financial packages";
				status obsolete;
			}

			enum "wetransfer" {
				opd:help "File hosting and sharing service";
				status obsolete;
			}

			enum "wfc" {
				opd:help "Wi-Fi Connection (WFC) is the Nintendo on-line gaming service for the Wii and DS videogame systems";
				status obsolete;
			}

			enum "whatsapp" {
				opd:help "WhatsApp Messenger is a cross-platform, instant, mobile messaging application which allows the users to exchange messages without having to pay for SMS";
				status obsolete;
			}

			enum "whois" {
				opd:help "WHOIS is a query and response protocol that is widely used for querying databases that store the registered users or assignees of an Internet resource, such as a domain name, an IP address block, or an autonomous system, but is also used for a wider range of other information";
				status obsolete;
			}

			enum "wiiconnect24" {
				opd:help "WiiConnect24 is an asynchronous communication protocol implemented on the Nintendo Wii gaming system";
				status obsolete;
			}

			enum "wikia" {
				opd:help "A free Wiki website hosting service";
				status obsolete;
			}

			enum "wikipedia" {
				opd:help "Wikipedia is the biggest multilingual free-content encyclopedia on the Internet";
				status obsolete;
			}

			enum "willhaben" {
				opd:help "Austrian online classified ads";
				status obsolete;
			}

			enum "wimp" {
				opd:help "WiMP is a music streaming service";
				status obsolete;
			}

			enum "winamax" {
				opd:help "Online gambling";
				status obsolete;
			}

			enum "windows_azure" {
				opd:help "Microsoft Azure is an enterprise cloud computing platform, providing SaaS and PaaS";
				status obsolete;
			}

			enum "windows_marketplace" {
				opd:help "Windows Marketplace is a service by Microsoft for its Windows Phone 7/8 and Microsoft Windows 8 platforms that allows users to browse and download applications that have been developed by third-parties";
				status obsolete;
			}

			enum "windows_update" {
				opd:help "Windows_update is the protocol used for windows system updates";
				status obsolete;
			}

			enum "windowslive" {
				opd:help "Windows Live is a signature which classifies generic web services related to the Microsoft Live platform";
				status obsolete;
			}

			enum "windowslivespace" {
				opd:help "This classifies the HTTP traffic to the host spaces.live.com";
				status obsolete;
			}

			enum "windowsmedia" {
				opd:help "This classifies the HTTP traffic to the host windowsmedia.com";
				status obsolete;
			}

			enum "winmx" {
				opd:help "WinMX is a freeware peer-to-peer file sharing program authored by Frontcode Technologies that runs on Microsoft Windows operating systems, and created in 2000";
				status obsolete;
			}

			enum "winny" {
				opd:help "Winny (also known as WinNY) is a Japanese peer-to-peer (P2P) file-sharing program";
				status obsolete;
			}

			enum "wins" {
				opd:help "WINS (Windows Internet Naming Service) is Microsoft's implementation of NetBIOS Name Service (NBNS), which is a name server and service for NetBIOS computer names";
				status obsolete;
			}

			enum "wiserearth" {
				opd:help "(Deprecated) This classifies the HTTP traffic to the host wiserearth.org";
				status obsolete;
			}

			enum "wix" {
				opd:help "Wix.com is a web development platform to create and host websites";
				status obsolete;
			}

			enum "wixi" {
				opd:help "This classifies the HTTP traffic to the host wixi.com";
				status obsolete;
			}

			enum "wooribank" {
				opd:help "This classifies the HTTP traffic to the host wooribank.com";
				status obsolete;
			}

			enum "word_online" {
				opd:help "On-line version of Microsoft Word";
				status obsolete;
			}

			enum "wordpress" {
				opd:help "WordPress is a popular blogging system";
				status obsolete;
			}

			enum "worksite" {
				opd:help "WorkSite is a Document Management System (DMS) application";
				status obsolete;
			}

			enum "wow" {
				opd:help "WOW is an online role-playing game";
				status obsolete;
			}

			enum "wp" {
				opd:help "Polish news portal";
				status obsolete;
			}

			enum "wretch" {
				opd:help "Taiwanese Photo Album and Blog";
				status obsolete;
			}

			enum "wrike" {
				opd:help "Wrike is web based project management software that gives you full visibility and control over your projects";
				status obsolete;
			}

			enum "wsman" {
				opd:help "SOAP-based protocol for managing computer systems (Web Services Management)";
				status obsolete;
			}

			enum "wsn" {
				opd:help "The wsn protocol (Wang Span Network) is found over the IP layer (IANA protocol number: 74)";
				status obsolete;
			}

			enum "wsop" {
				opd:help "Mobile game";
				status obsolete;
			}

			enum "wsp" {
				opd:help "Wireless Session Protocol (WSP) is an application layer protocol present in the WAP stack";
				status obsolete;
			}

			enum "wtls" {
				opd:help "Wireless Transport Layer Security (WTLS) is a security protocol, part of the WAP stack";
				status obsolete;
			}

			enum "wtp" {
				opd:help "Wireless Transaction Protocol (WTP) is a transport layer protocol which belongs to the WAP stack";
				status obsolete;
			}

			enum "wtv" {
				opd:help "WTV Networks is an entertainment and show biz news website";
				status obsolete;
			}

			enum "x11" {
				opd:help "X11 is designed to communicate all the information necessary to operate a window system over a single asynchronous bi-directional stream of 8-bit bytes";
				status obsolete;
			}

			enum "x25" {
				opd:help "X.25 is a packet switched data network protocol which defines an international recommendation for the exchange of data as well as control information between a user device (host), called Data Terminal Equipment (DTE) and a network node, called Data Circuit Terminating Equipment (DCE)";
				status obsolete;
			}

			enum "xanga" {
				opd:help "This classifies the traffic to the host xanga.com";
				status obsolete;
			}

			enum "xbox" {
				opd:help "This classifies generic traffic to the Xbox web portal";
				status obsolete;
			}

			enum "xbox_music" {
				opd:help "Xbox Music is an online service for music";
				status obsolete;
			}

			enum "xbox_video" {
				opd:help "Microsoft Movies and TV is an online service to watch movies, TV show and series";
				status obsolete;
			}

			enum "xboxlive" {
				opd:help "Online multiplayer gaming and digital media delivery service created and operated by Microsoft Corporation";
				status obsolete;
			}

			enum "xboxlive_marketplace" {
				opd:help "Xbox Live Marketplace is a service where users can purchase and download games and multimedia";
				status obsolete;
			}

			enum "xcams" {
				opd:help "Xcams is an adult webcam website";
				status obsolete;
			}

			enum "xcap" {
				opd:help "Xcap (XML Configuration Access Protocol) protocol in VoLTE environment is used to setup, enable or disable the Supplementary Services available for a user";
				status obsolete;
			}

			enum "xdmcp" {
				opd:help "XDMCP is an extension of the X11 protocol that addresses the issue of discovering and authenticating available X servers on the LAN";
				status obsolete;
			}

			enum "xendan" {
				opd:help "Iranian news portal";
				status obsolete;
			}

			enum "xfs" {
				opd:help "X Font Server is a standard communication protocol between an X server and a font renderer";
				status obsolete;
			}

			enum "xhamster" {
				opd:help "Pornographic videos streaming platform";
				status obsolete;
			}

			enum "xiami" {
				opd:help "Chinese Music P2P community website";
				status obsolete;
			}

			enum "xiaomi" {
				opd:help "Xiaomi is a privately owned Chinese electronics company";
				status obsolete;
			}

			enum "xing" {
				opd:help "This classifies the HTTP traffic to the host xing.com";
				status obsolete;
			}

			enum "xinhuanet" {
				opd:help "This classifies the HTTP traffic to the host xinhuanet.com";
				status obsolete;
			}

			enum "xinnet" {
				opd:help "Xinnet provides web-hosting, and mailbox services in China";
				status obsolete;
			}

			enum "xiph" {
				opd:help "Xiph is non-profit corporation dedicated to protecting multimedia from control by private interests";
				status obsolete;
			}

			enum "xl" {
				opd:help "Portuguese multisites and portal";
				status obsolete;
			}

			enum "xl_nonton" {
				opd:help "XL Nonton offers access streaming contents via PC and Smartphone";
				status obsolete;
			}

			enum "xl_wap" {
				opd:help "This classifies the HTTP traffic to the host wap.xl.co.id";
				status obsolete;
			}

			enum "xl_webmail" {
				opd:help "This classifies the HTTP traffic to the host webmail.xl.co.id";
				status obsolete;
			}

			enum "xl_webportal" {
				opd:help "Indonesian mobile telecommunications services operator web portal";
				status obsolete;
			}

			enum "xlnet" {
				opd:help "This classifies the HTTP traffic to the host xl.net.id";
				status obsolete;
			}

			enum "xlovecam" {
				opd:help "Xlovecam is an adult webcam website";
				status obsolete;
			}

			enum "xm_radio" {
				opd:help "This classifies the HTTP traffic to the hosts xmradio.com and siriusxm.com";
				status obsolete;
			}

			enum "xmcp" {
				opd:help "Cisco External Client Protocol to interact with service routing-enabled network";
				status obsolete;
			}

			enum "xmlrpc" {
				opd:help "XMLRPC is a remote procedure calling using HTTP as the transport and XML as the encoding";
				status obsolete;
			}

			enum "xnet" {
				opd:help "The xnet protocol (Cross Net Debugger) is found over the IP layer (IANA protocol number: 15)";
				status obsolete;
			}

			enum "xns" {
				opd:help "Xerox Network Systems is a protocol suite originally designed by Xerox PARC";
				status obsolete;
			}

			enum "xns_idp" {
				opd:help "The xns_idp protocol (XEROX NS IDP) is found over the IP layer (IANA protocol number: 22)";
				status obsolete;
			}

			enum "xnxx" {
				opd:help "XNXX is a popular adult video streaming website";
				status obsolete;
			}

			enum "xopom" {
				opd:help "Mongolian free news portal site";
				status obsolete;
			}

			enum "xot" {
				opd:help "Protocol used to transport x25 data over TCP in IP network";
				status obsolete;
			}

			enum "xrea" {
				opd:help "This classifies the HTTP traffic to the host xrea.com";
				status obsolete;
			}

			enum "xt3" {
				opd:help "This classifies the HTTP and SSL traffic to the host xt3.com";
				status obsolete;
			}

			enum "xtp" {
				opd:help "The xtp protocol (XTP) is found over the IP layer (IANA protocol number: 36)";
				status obsolete;
			}

			enum "xuite" {
				opd:help "Taiwanese blog platform, media file sharing, online games";
				status obsolete;
			}

			enum "xvideos" {
				opd:help "Xvideos is a free adult videos website";
				status obsolete;
			}

			enum "xvideoslive" {
				opd:help "Xvideos Live is an adult live webcam website";
				status obsolete;
			}

			enum "xyplex" {
				opd:help "Xyplex is used to communicate with Xyplex servers";
				status obsolete;
			}

			enum "y8" {
				opd:help "Y8.com has Free Online Mini Games in both Flash and Shockwave";
				status obsolete;
			}

			enum "yadro" {
				opd:help "Yadro is an advertising company that is part of a network of sites and other technologies";
				status obsolete;
			}

			enum "yahoo" {
				opd:help "Yahoo is a pseudo-protocol which classifies generic web services related to Yahoo";
				status obsolete;
			}

			enum "yahoo360plusvietnam" {
				opd:help "This classifies the HTTP traffic to the host vn.360plus.yahoo.com";
				status obsolete;
			}

			enum "yahoo_answers" {
				opd:help "This classifies the HTTP traffic to the host answers.yahoo.com";
				status obsolete;
			}

			enum "yahoo_biz" {
				opd:help "(Deprecated) This classifies the HTTP traffic to the hosts fr.biz.yahoo.com and finance.yahoo.com";
				status obsolete;
			}

			enum "yahoo_buy" {
				opd:help "Yahoo Taiwanese Shopping portal";
				status obsolete;
			}

			enum "yahoo_douga" {
				opd:help "This classifies the HTTP traffic to the host streaming.yahoo.co.jp";
				status obsolete;
			}

			enum "yahoo_games" {
				opd:help "This classifies the HTTP traffic to the host games.yahoo.com";
				status obsolete;
			}

			enum "yahoo_geocities" {
				opd:help "This classifies the HTTP traffic to the host geocities.yahoo.com";
				status obsolete;
			}

			enum "yahoo_groups" {
				opd:help "Yahoo! Groups offers free mailing lists, photo and file sharing, group calendars and more";
				status obsolete;
			}

			enum "yahoo_korea" {
				opd:help "This classifies the HTTP traffic to the hosts yahoo.co.kr and kr.yahoo.com";
				status obsolete;
			}

			enum "yahoo_maps" {
				opd:help "Yahoo Maps can be used to calculate routes or to look at maps";
				status obsolete;
			}

			enum "yahoo_realestate" {
				opd:help "This classifies the HTTP traffic to the hosts realestate.yahoo.com and homes.yahoo.com";
				status obsolete;
			}

			enum "yahoo_screen" {
				opd:help "This classifies the HTTP traffic to the host screen.yahoo.com";
				status obsolete;
			}

			enum "yahoo_search" {
				opd:help "This protocol is used to send queries to the Yahoo search engine";
				status obsolete;
			}

			enum "yahoo_stock_tw" {
				opd:help "Yahoo finance Taiwanese portal";
				status obsolete;
			}

			enum "yahoo_travel" {
				opd:help "This classifies the HTTP traffic to the hosts travel.yahoo.com and fr.voyage.yahoo.com";
				status obsolete;
			}

			enum "yallakora" {
				opd:help "Egyptian football related website";
				status obsolete;
			}

			enum "yam" {
				opd:help "This classifies the traffic to the host yam.com";
				status obsolete;
			}

			enum "yammer" {
				opd:help "Private social network solution for enterprises";
				status obsolete;
			}

			enum "yandex" {
				opd:help "Yandex is a Russian search engine";
				status obsolete;
			}

			enum "yandex_disk" {
				opd:help "Yandex Disk is a Russian file sharing service";
				status obsolete;
			}

			enum "yandex_fotki" {
				opd:help "Yandex Fotki (Yandex Photos) is the Yandex photo service";
				status obsolete;
			}

			enum "yandex_maps" {
				opd:help "Yandex Maps is the Yandex map service";
				status obsolete;
			}

			enum "yandex_music" {
				opd:help "Yandex Music is a music and radio streaming web service by Yandex";
				status obsolete;
			}

			enum "yandex_video" {
				opd:help "Yandex Video is a video streaming web portal showing Youtube videos";
				status obsolete;
			}

			enum "yandex_webmail" {
				opd:help "Yandex webmail is the Russian webmail on webmail.yandex.ru";
				status obsolete;
			}

			enum "yapo" {
				opd:help "Chilean classified ads website";
				status obsolete;
			}

			enum "yasour" {
				opd:help "Generic content and entertainment website in Lebanon";
				status obsolete;
			}

			enum "yelp" {
				opd:help "This classifies the HTTP traffic to the host yelp.com";
				status obsolete;
			}

			enum "yemen_net" {
				opd:help "Yemeni service provider portal";
				status obsolete;
			}

			enum "yemennow" {
				opd:help "Yemeni news portal";
				status obsolete;
			}

			enum "yen" {
				opd:help "Ghanian news and entertainment web portal";
				status obsolete;
			}

			enum "yesky" {
				opd:help "This classifies the HTTP traffic to the host yesky.com";
				status obsolete;
			}

			enum "yieldmanager" {
				opd:help "Yield Manager is an advertising delivery technology operated by Right Media";
				status obsolete;
			}

			enum "yieldmo" {
				opd:help "Yieldmo is a mobile advertising technology company";
				status obsolete;
			}

			enum "yihaodian" {
				opd:help "Chinese Online shopping";
				status obsolete;
			}

			enum "yle" {
				opd:help "Finnish news portal";
				status obsolete;
			}

			enum "ymail2" {
				opd:help "This protocol is the ajax based version of Webmail Yahoo";
				status obsolete;
			}

			enum "ymail_classic" {
				opd:help "Yahoo! Mail Classic was the original interface for Yahoo! Mail";
				status obsolete;
			}

			enum "ymail_mobile" {
				opd:help "(Deprecated) Yahoo Mail Mobile is the yahoo.com webmail adapted to mobiles";
				status obsolete;
			}

			enum "ymail_mobile_new" {
				opd:help "Yahoo Mail Mobile_new is the new yahoo.com webmail adapted to mobiles";
				status obsolete;
			}

			enum "ymsg" {
				opd:help "(Deprecated) Yahoo Messenger is used by the Yahoo Instant Messenger application to send instant messages, files and emails between users";
				status obsolete;
			}

			enum "ymsg_conf" {
				opd:help "(Deprecated) This protocol is used in signaling part in a conference";
				status obsolete;
			}

			enum "ymsg_transfer" {
				opd:help "(Deprecated) This protocol is used for file transfers over ymsg";
				status obsolete;
			}

			enum "ymsg_video" {
				opd:help "This protocol is used by Yahoo Messenger for video conversations";
				status obsolete;
			}

			enum "ymsg_webmessenger" {
				opd:help "(Deprecated) Yahoo webmessenger";
				status obsolete;
			}

			enum "ynet" {
				opd:help "Israeli news portal";
				status obsolete;
			}

			enum "yodiz" {
				opd:help "Yodiz is online Agile Project Management tool, consisting of Product Backlog Management, Kanban Scrum Board, Issue Tracking Software, Team Discussions and issues";
				status obsolete;
			}

			enum "yoka" {
				opd:help "Chinese fashion portal";
				status obsolete;
			}

			enum "yomiuri" {
				opd:help "Japanese news website";
				status obsolete;
			}

			enum "yoono" {
				opd:help "This classifies the HTTP traffic to the host yoono.com";
				status obsolete;
			}

			enum "youdao" {
				opd:help "This classifies the HTTP traffic to the host youdao.com";
				status obsolete;
			}

			enum "youku" {
				opd:help "Youku is a Chinese video hosting web service";
				status obsolete;
			}

			enum "youm7" {
				opd:help "This classifies the HTTP traffic to the host youm7.com";
				status obsolete;
			}

			enum "youmeo" {
				opd:help "This classifies the HTTP and SSL traffic to the host calumbrannan.com";
				status obsolete;
			}

			enum "youni" {
				opd:help "Youni SMS is a totally free mobile messaging application";
				status obsolete;
			}

			enum "younow" {
				opd:help "YouNow is a live webcast service";
				status obsolete;
			}

			enum "youporn" {
				opd:help "Youporn is a popular adult video streaming website";
				status obsolete;
			}

			enum "your_freedom" {
				opd:help "VPN tunneling and anonymization application";
				status obsolete;
			}

			enum "yourfilehost" {
				opd:help "(Deprecated) This used to classify the HTTP traffic to the yourfilehost.com service";
				status obsolete;
			}

			enum "yourfiles_biz" {
				opd:help "Classifies web browsing on the yourfiles.biz Direct DownLoad links service";
				status obsolete;
			}

			enum "youseemore" {
				opd:help "This classifies the HTTP traffic to the host youseemore.com";
				status obsolete;
			}

			enum "yousendit" {
				opd:help "Cloud file storage service with professional services";
				status obsolete;
			}

			enum "youtube" {
				opd:help "Youtube is a website where users can send or watch videos";
				status obsolete;
			}

			enum "youtube_hd" {
				opd:help "(Deprecated) Youtube HD classification ensures that the user is watching a High Definition video (at least 720 lines)";
				status obsolete;
			}

			enum "ypbind" {
				opd:help "The ypbind utility is the process that maintains NIS binding information";
				status obsolete;
			}

			enum "yppasswd" {
				opd:help "The Yellow Page Password protocol enables the modification of logins and passwords in Network Interface System cards";
				status obsolete;
			}

			enum "ypserv" {
				opd:help "Yellow Pages Server is a protocol used to distribute NIS databases to client systems within a NIS domain";
				status obsolete;
			}

			enum "ypupdate" {
				opd:help "The Yellow Pages Update protocol enables information updates in Network Information Services (NIS) cards";
				status obsolete;
			}

			enum "yr" {
				opd:help "Norwegian meteorological website";
				status obsolete;
			}

			enum "ytimg" {
				opd:help "(Deprecated) This classified the HTTP traffic to the host ytimg.com";
				status obsolete;
			}

			enum "yugma" {
				opd:help "This classifies the HTTP traffic to the host yugma.com";
				status obsolete;
			}

			enum "yuuguu" {
				opd:help "This classifies the HTTP traffic to the host share.yuuguu.com";
				status obsolete;
			}

			enum "zabbix_agent" {
				opd:help "Agent for Zabbix monitoring server";
				status obsolete;
			}

			enum "zahraa" {
				opd:help "Global news website from Mauritania";
				status obsolete;
			}

			enum "zalo" {
				opd:help "Zalo is a Vietnamese mobile IM application created by VNG Corporation with audio/image file send feature";
				status obsolete;
			}

			enum "zaluu" {
				opd:help "Mongolian news portal";
				status obsolete;
			}

			enum "zambiawatchdog" {
				opd:help "Breaking and investigative news on Zambia";
				status obsolete;
			}

			enum "zamunda" {
				opd:help "Bulgarian Torrent tracker";
				status obsolete;
			}

			enum "zattoo" {
				opd:help "Zattoo is website and a set of peer-to-peer TV applications";
				status obsolete;
			}

			enum "zedo" {
				opd:help "Zedo is a global advertisement solution provider";
				status obsolete;
			}

			enum "zelune" {
				opd:help "HTTP redirector service (anonymizing proxy)";
				status obsolete;
			}

			enum "zendesk" {
				opd:help "Zendesk is a cloud-based customer service platform, that includes ticketing, self-service options, and customer support features";
				status obsolete;
			}

			enum "zenmate" {
				opd:help "ZenMate is a web-browser extension that provides VPN-like protection";
				status obsolete;
			}

			enum "zeri" {
				opd:help "Zeri newspaper, voice portal and mobile independent media portal, popular in Albania";
				status obsolete;
			}

			enum "zhihu" {
				opd:help "Famous Chinese question-and-answer website";
				status obsolete;
			}

			enum "ziddu" {
				opd:help "Ziddu is an online solution to upload and share files";
				status obsolete;
			}

			enum "zimbra" {
				opd:help "Zimbra provides open source server and client software for messaging and collaboration";
				status obsolete;
			}

			enum "zimbra_standard" {
				opd:help "Zimbra Standard is the Standard interface version of the Zimbra Webmail client";
				status obsolete;
			}

			enum "zimeye" {
				opd:help "Popular news portal in Zimbabwe";
				status obsolete;
			}

			enum "zing" {
				opd:help "Vietnamese classified ads";
				status obsolete;
			}

			enum "zippyshare" {
				opd:help "File hosting and sharing services";
				status obsolete;
			}

			enum "zoho" {
				opd:help "Zoho is a software development company providing online office suite named Zoho Office Suite";
				status obsolete;
			}

			enum "zoho_crm" {
				opd:help "This classifies the HTTP traffic to the host crm.zoho.com";
				status obsolete;
			}

			enum "zoho_db" {
				opd:help "The ZOHO DB and Reports is an online database and reporting application";
				status obsolete;
			}

			enum "zoho_im" {
				opd:help "Multi-protocol Instant Messaging web service owned by ZOHO Corp";
				status obsolete;
			}

			enum "zoho_meeting" {
				opd:help "This classifies the HTTP traffic to the hosts wms8.zoho.com, chat.zoho.com and meeting.zoho.com";
				status obsolete;
			}

			enum "zoho_notebook" {
				opd:help "Zoho Notebook application classification";
				status obsolete;
			}

			enum "zoho_people" {
				opd:help "This classifies the HTTP traffic to the host wms2.zoho.com";
				status obsolete;
			}

			enum "zoho_planner" {
				opd:help "Zoho Planner application classification";
				status obsolete;
			}

			enum "zoho_share" {
				opd:help "Zoho Share application classification";
				status obsolete;
			}

			enum "zoho_sheet" {
				opd:help "Zoho Sheet application classification";
				status obsolete;
			}

			enum "zoho_show" {
				opd:help "Zoho Show application classification";
				status obsolete;
			}

			enum "zol" {
				opd:help "This classifies the HTTP traffic to the host zol.com.cn";
				status obsolete;
			}

			enum "zombie_tsunami" {
				opd:help "Mobile game";
				status obsolete;
			}

			enum "zone_telechargement" {
				opd:help "Pirate Direct DownLoad website featuring movies and series";
				status obsolete;
			}

			enum "zonealarm_update" {
				opd:help "ZoneAlarm is a personal firewall for Windows";
				status obsolete;
			}

			enum "zoo" {
				opd:help "This classifies the HTTP traffic to the host zoo.gr";
				status obsolete;
			}

			enum "zoom" {
				opd:help "Zoom Video Conferencing, also referred to as Zoom by users, combines video conferencing, online meetings, and mobile collaboration into one platform";
				status obsolete;
			}

			enum "zoomtanzania" {
				opd:help "Classified ads and real estate website in Tanzania";
				status obsolete;
			}

			enum "zopim" {
				opd:help "Zopim is a live chat software owned by Zendesk";
				status obsolete;
			}

			enum "zougla" {
				opd:help "Greek news portal";
				status obsolete;
			}

			enum "zoznam" {
				opd:help "Slovakian internet portal";
				status obsolete;
			}

			enum "zshare" {
				opd:help "zShare is an online solution to store, send and share files";
				status obsolete;
			}

			enum "zuji" {
				opd:help "Singaporean online travel agency";
				status obsolete;
			}

			enum "zum" {
				opd:help "This classifies the HTTP traffic to the host zum.com";
				status obsolete;
			}

			enum "zumodrive" {
				opd:help "ZumoDrive is a cloud-based file synchronization and storage service";
				status obsolete;
			}

			enum "zwherald" {
				opd:help "News portal from Zimbabwe";
				status obsolete;
			}

			enum "zynga" {
				opd:help "Zynga is a social network oriented on-line video games editor";
				status obsolete;
			}

			enum "abn_amro_bankieren" {
				opd:help "ABN AMRO is a Dutch bank with headquarters in Amsterdam";
				status obsolete;
			}

			enum "bacnet_app" {
				opd:help "BACnet is a communication protocol for Building Automation and Control (BAC) networks defined by the standard ISO 16484-5";
				status obsolete;
			}

			enum "bacnet_net" {
				opd:help "BACnet is a communication protocol for Building Automation and Control (BAC) networks defined by the standard ISO 16484-5";
				status obsolete;
			}

			enum "bacnet_vlc" {
				opd:help "BACnet is a communication protocol for Building Automation and Control (BAC) networks defined by the standard ISO 16484-5";
				status obsolete;
			}

			enum "cabify" {
				opd:help "Cabify is an international transportation network company";
				status obsolete;
			}

			enum "canvas" {
				opd:help "Canvas Student is an educational application";
				status obsolete;
			}

			enum "chinanetcenter" {
				opd:help "ChinaNetCenter is an Internet service platform provider and a CDN";
				status obsolete;
			}

			enum "chunghwa_telecom" {
				opd:help "Services and websites provided by Chunghwa Telecom";
				status obsolete;
			}

			enum "citrix_cloud" {
				opd:help "Citrix Cloud is a cloud-based platform for managing and deploying Citrix products";
				status obsolete;
			}

			enum "clash_royale" {
				opd:help "Clash Royale is an online mobile game by Supercell";
				status obsolete;
			}

			enum "csp_abethernet" {
				opd:help "Proprietary protocol developed by Allen-Bradley, used on programmable logical controllers (PLC)";
				status obsolete;
			}

			enum "dcard" {
				opd:help "Dcard is a social network application on mobile devices";
				status obsolete;
			}

			enum "dota2" {
				opd:help "Dota2 2 is a free-to-play multiplayer online battle arena (MOBA) video game developed and published by Valve Corporation";
				status obsolete;
			}

			enum "echo360" {
				opd:help "Echo360 application allows users to build online courses and plan/share them with students";
				status obsolete;
			}

			enum "electronic_arts" {
				opd:help "This classifies the generic web traffic related to Electronic Arts";
				status obsolete;
			}

			enum "facebook_lite" {
				opd:help "Facebook Lite is an official Facebook client that allows using this popular social network through a much lighter app";
				status obsolete;
			}

			enum "facebook_workplace" {
				opd:help "Workplace by Facebook is a social network for enterprises";
				status obsolete;
			}

			enum "furk_net" {
				opd:help "Furk.net is a cloud file storage service";
				status obsolete;
			}

			enum "gcp" {
				opd:help "Google Cloud Platform is a suite of cloud computing services that runs on the same infrastructure that Google uses internally for its end-user products";
				status obsolete;
			}

			enum "hami_book" {
				opd:help "Traffic from hamibook website";
				status obsolete;
			}

			enum "hami_cloud" {
				opd:help "Traffic from hamicloud website";
				status obsolete;
			}

			enum "hami_music" {
				opd:help "Traffic from Hami Music website";
				status obsolete;
			}

			enum "haproxy" {
				opd:help "HAProxy is free, open source software that provides a high availability load balancer and proxy server for TCP and HTTP-based applications";
				status obsolete;
			}

			enum "horizon_go" {
				opd:help "Horizon GO provides live TV, streams movies and series on demand";
				status obsolete;
			}

			enum "hulkshare" {
				opd:help "Free Internet Radio service featuring personal audio file uploading and sharing";
				status obsolete;
			}

			enum "instructure" {
				opd:help "Instructure is a learning technology company and the creator of the Canvas learning management system";
				status obsolete;
			}

			enum "join_me" {
				opd:help "This signature detects Join.me, a free service that allows to share a desktop instantly with others";
				status obsolete;
			}

			enum "kahoot" {
				opd:help "Kahoot! is a free game-based learning platform";
				status obsolete;
			}

			enum "kkbox" {
				opd:help "Traffic from KKBOX website";
				status obsolete;
			}

			enum "krcom" {
				opd:help "krcom.cn is a Chinese video website";
				status obsolete;
			}

			enum "lotro" {
				opd:help "The Lord of the Rings Online is a video game of type MMORPG inspired by the world of The Lord of the Rings";
				status obsolete;
			}

			enum "m800" {
				opd:help "M800 provides communication products and solutions";
				status obsolete;
			}

			enum "mail_com" {
				opd:help "Mail.com is a web portal and web-based email service provider owned by the German internet company United Internet";
				status obsolete;
			}

			enum "meitu" {
				opd:help "Meitu is an online mobile photo-sharing and social networking service";
				status obsolete;
			}

			enum "mongodb" {
				opd:help "Mongodb is a relational database management system (RDBMS)";
				status obsolete;
			}

			enum "ms_mq" {
				opd:help "Message Queuing (MSMQ) technology enables applications running at different times to communicate across heterogeneous networks and systems that may be temporarily offline";
				status obsolete;
			}

			enum "ms_teams" {
				opd:help "Microsoft Teams is the chat-based workspace in Office 365";
				status obsolete;
			}

			enum "msnp" {
				opd:help "Microsoft Notification Protocol (MSNP, also known as the Mobile Status Notification Protocol) is an instant messaging protocol developed by Microsoft for use by the Microsoft Messenger service and the instant messaging clients that connect to it, such as Skype since 2014";
				status obsolete;
			}

			enum "nepworldwide" {
				opd:help "NEP Worldwide is a video broadcaster";
				status obsolete;
			}

			enum "netvelocity" {
				opd:help "NetVelocity enables users to test, measure, compare and share their network performance";
				status obsolete;
			}

			enum "network_radar" {
				opd:help "Network Radar is a network scanning and managing tool";
				status obsolete;
			}

			enum "niantic" {
				opd:help "Niantic, Inc. is an American software development company";
				status obsolete;
			}

			enum "origin" {
				opd:help "Origin is a gaming download platform available on the web at www.origin.com";
				status obsolete;
			}

			enum "perfect_world_ent" {
				opd:help "Perfect World Entertainment is Perfect World's North American online games publisher specializing in free-to-play PC games";
				status obsolete;
			}

			enum "pornhub_network" {
				opd:help "Adult Content Delivery Network used by popular adult video streaming website like youporn, pornhub, redtube and tube8";
				status obsolete;
			}

			enum "ptt" {
				opd:help "PTT is a Taiwanese BBS website (Bulletin Board System)";
				status obsolete;
			}

			enum "pwi" {
				opd:help "PWI is a free gaming MMORPG offering an unparalleled character customization tool and a unique gameplay style in a magical universe";
				status obsolete;
			}

			enum "rabo_bankieren" {
				opd:help "Dutch online banking website";
				status obsolete;
			}

			enum "s7comm" {
				opd:help "S7comm (S7 Communication) is a Siemens proprietary protocol that runs between programmable logic controllers (PLCs) of the Siemens S7-300/400 family";
				status obsolete;
			}

			enum "sharefile_com" {
				opd:help "Citrix ShareFile is a secure enterprise file sharing and sync (EFSS) solution";
				status obsolete;
			}

			enum "shopee" {
				opd:help "shopee is an online shopping platform";
				status obsolete;
			}

			enum "simple_speedtest" {
				opd:help "Simple Speed Test helps to monitor network connection (bandwidth, upload, download and ping latency) from smartphone or web browser";
				status obsolete;
			}

			enum "snow" {
				opd:help "SNOW is a video messaging application";
				status obsolete;
			}

			enum "speedcheck_internet" {
				opd:help "Speedcheck tests the speed of internet connections and adds your results to SpeedSpot's WiFi speed database";
				status obsolete;
			}

			enum "sportradar" {
				opd:help "Sportradar collects and analyzes sports data";
				status obsolete;
			}

			enum "starcraft2" {
				opd:help "Starcraft 2 is a real-time strategy video game";
				status obsolete;
			}

			enum "streamroot" {
				opd:help "Distributed Network Architecture for OTT Video Delivery";
				status obsolete;
			}

			enum "t_mobile_app" {
				opd:help "T-Mobile is a global mobile phone operator";
				status obsolete;
			}

			enum "t_mobile_cloud" {
				opd:help "T-Mobile Cloud is the T-Mobile cloud service";
				status obsolete;
			}

			enum "trai_myspeed" {
				opd:help "This application measures your data speed experience and sends the results to TRAI";
				status obsolete;
			}

			enum "united_internet" {
				opd:help "United Internet is one of a European internet companies";
				status obsolete;
			}

			enum "uplive" {
				opd:help "Uplive is a social network mobile for live streaming around the world";
				status obsolete;
			}

			enum "videoland" {
				opd:help "Videoland is a video-on-demand service, when video streaming is hosted on NEP Worldwide servers, this traffic is classified as nepworldwide";
				status obsolete;
			}

			enum "vivox" {
				opd:help "Vivox provides managed communication services in the form of integrated voice chat, Instant Messaging (IM) to online games, virtual worlds and other online communities";
				status obsolete;
			}

			enum "vk_live" {
				opd:help "VK Live is an app for live streaming on VK (a popular Social Network in Russia)";
				status obsolete;
			}

			enum "wallstreetjournal" {
				opd:help "The Wall Street Journal is a US national daily";
				status obsolete;
			}

			enum "world_of_tanks" {
				opd:help "World Of Tanks is a massively multiplayer online Belarusian game developed by Wargaming.net company";
				status obsolete;
			}

			enum "apptimize" {
				opd:help "Apptimize provides tools for A/B Testing, Feature Release Management, and Optimization for Mobile, Web, and OTT apps";
				status obsolete;
			}

			enum "aumix" {
				opd:help "AUMIX Internet Solutions is a service provider and a hosting company";
				status obsolete;
			}

			enum "bf1" {
				opd:help "Battlefield 1 is a first-person shooter video game published by Electronic Arts and released in October 2016";
				status obsolete;
			}

			enum "bf4" {
				opd:help "Battlefield 4 is a first-person shooter video game published by Electronic Arts";
				status obsolete;
			}

			enum "deltav" {
				opd:help "Traffic related to DeltaV, a distributed control system used in industrial process control (Emerson Process Management)";
				status obsolete;
			}

			enum "digioh" {
				opd:help "Digioh is a lead generation and marketing company";
				status obsolete;
			}

			enum "fasp" {
				opd:help "Fast Adaptative and Secure Protocol (FASP) is developed by the company Aspera";
				status obsolete;
			}

			enum "goodnight" {
				opd:help "Goodnight is a simple voice-chat app for calling and chatting for free, focused on the Korean, Chinese, and Anglophone markets";
				status obsolete;
			}

			enum "huomao" {
				opd:help "Huomao is a streaming video platform for gamers";
				status obsolete;
			}

			enum "ifix" {
				opd:help "Formerly Proficy HMI/SCADA iFIX, is an industrial automation system";
				status obsolete;
			}

			enum "kakao" {
				opd:help "Kakao is a Korean company specializing in internet services";
				status obsolete;
			}

			enum "mediascope" {
				opd:help "Mediascope provides media and marketing information";
				status obsolete;
			}

			enum "ms_hyperv" {
				opd:help "Microsoft Hyper-V is a native hypervisor for Windows operating systems";
				status obsolete;
			}

			enum "ms_kms" {
				opd:help "Key Management Service (KMS) activates computers on a local network, eliminating the need for individual computers to connect to Microsoft";
				status obsolete;
			}

			enum "ms_psrp" {
				opd:help "Client applications use the MicroSoft PowerShell Remoting Protocol (MS PSRP) to send pipelines of commands to a server system over a network for execution by the server";
				status obsolete;
			}

			enum "shareman" {
				opd:help "Shareman is a peer-to-peer file sharing and streaming network";
				status obsolete;
			}

			enum "temasys" {
				opd:help "Temasys provides cloud-based WebRTC infrastructure and developer-centric SDKs for embedding real-time communications into web or mobile apps for interactive video, voice and data communications";
				status obsolete;
			}

			enum "thrift" {
				opd:help "Apache Thrift framework used for serialisation";
				status obsolete;
			}

			enum "uc_browser" {
				opd:help "UC Browser is a web browser developed by the Chinese mobile Internet company UCWeb and is owned by Alibaba Group of China";
				status obsolete;
			}

			enum "vero" {
				opd:help "Vero is social network to change usual social network business models";
				status obsolete;
			}

			enum "wmi" {
				opd:help "Windows Management Instrumentation (WMI) is the Microsoft implementation of the Web-Based Enterprise Management (WBEM)";
				status obsolete;
			}

			enum "youtube_kids" {
				opd:help "YouTube Kids is an application providing a family-friendly version of YouTube for younger children, with parental control features and video filter";
				status obsolete;
			}

			enum "zonealarm" {
				opd:help "ZoneAlarm is a personal firewall for Windows";
				status obsolete;
			}

			enum "9gag" {
				opd:help "9gag is a humorous website or application based on the sharing of images and videos";
				status obsolete;
			}

			enum "9p" {
				opd:help "9P is a network protocol developed by Bell Labs and distributed in their Operating System Plan 9";
				status obsolete;
			}

			enum "adtelligent" {
				opd:help "Adtelligent Inc. is an advertising technology company";
				status obsolete;
			}

			enum "akamai_video" {
				opd:help "Akamai Video is the Akamai cloud service for video streaming (used for Media Services Live, the Old HD Flash 1.0 Solution, and Media Services On-Demand technologies)";
				status obsolete;
			}

			enum "alicall" {
				opd:help "Alicall is a Chinese application that provide International VoIP call feature";
				status obsolete;
			}

			enum "anchorfree" {
				opd:help "AnchorFree is an anonymous VPN software released by Betternet (formerly vpnintouch) company";
				status obsolete;
			}

			enum "appnext" {
				opd:help "Appnext is mobile monetization, app marketing & re-engagement platform";
				status obsolete;
			}

			enum "arte_tv" {
				opd:help "Arte TV is a Franco-German television channel";
				status obsolete;
			}

			enum "avamar" {
				opd:help "AVAMAR is a backup system distributed by Dell EMC offering data deduplication";
				status obsolete;
			}

			enum "azure_rms" {
				opd:help "Azure Rights Management Service is a Microsoft rights management service for files and Office documents which acts like a DRM license server";
				status obsolete;
			}

			enum "barracuda" {
				opd:help "Barracuda Networks, Inc. is a company providing security, networking and storage products based on network appliances and cloud services";
				status obsolete;
			}

			enum "barracuda_vpn" {
				opd:help "Appliance edited by Barracuda and providing VPN service";
				status obsolete;
			}

			enum "bigbigchannel" {
				opd:help "Big Big Channel is an online video platform operated by TVB";
				status obsolete;
			}

			enum "brawlhalla" {
				opd:help "Brawlhalla is a free to play battle arena on-line multiplayer game edited by Blue Mammoth Games and plublished by Ubisoft";
				status obsolete;
			}

			enum "bytedance" {
				opd:help "ByteDance is a Chinese company that publishes several applications including TikTok (aka Musically), BuzzVideo and Vigo Video";
				status obsolete;
			}

			enum "call_of_duty" {
				opd:help "Call of duty (aka COD) is a video game First Person Shooter (FPS) available on Xbox, PS4, Microsoft windows and published by Activision";
				status obsolete;
			}

			enum "cisco" {
				opd:help "Cisco Systems, Inc. is an American multinational technology";
				status obsolete;
			}

			enum "cisco_ap" {
				opd:help "This plugin identifies capwap control flows specific to CISCO Access Point devices";
				status obsolete;
			}

			enum "cisco_cmx_cloud" {
				opd:help "Cisco Connected Mobile Experiences (CMX) Cloud is a cloud-delivered version of the on-premises CMX 10 software";
				status obsolete;
			}

			enum "cisco_corp_tv" {
				opd:help "Cisco Corporate TV is an interactive web streaming, and live studio shows platform";
				status obsolete;
			}

			enum "cisco_ip_sla" {
				opd:help "Cisco IP SLA is used to monitor IP applications by using active traffic";
				status obsolete;
			}

			enum "cisco_rrm" {
				opd:help "Cisco Wireless LAN controller coordinates a set of Cisco wireless LAN access points";
				status obsolete;
			}

			enum "cisco_sdavc" {
				opd:help "Cisco Software-Defined AVC (SD-AVC) is a component of Cisco Application Visibility and Control (AVC)";
				status obsolete;
			}

			enum "cisco_spark" {
				opd:help "Cisco Spark (aka Cisco Webex teams) is a communication and collaboration service, delivered from the Cisco Collaboration Cloud";
				status obsolete;
			}

			enum "cisco_ucm" {
				opd:help "Cisco Unified Communication Manager is an IP PBX for enterprises";
				status obsolete;
			}

			enum "cmore" {
				opd:help "CMORE is a Swedish distributor of paid videos on demand";
				status obsolete;
			}

			enum "coco" {
				opd:help "Coco is an instant messaging application with VoIP feature";
				status obsolete;
			}

			enum "data_saver" {
				opd:help "Data Saver is an optional feature in Chrome";
				status obsolete;
			}

			enum "demonware" {
				opd:help "DemonWare is a software development company and a subsidiary of Activision Blizzard, Inc";
				status obsolete;
			}

			enum "diablo3" {
				opd:help "Diablo III is a hack and slash action role-playing video game developed and published by Blizzard Entertainment";
				status obsolete;
			}

			enum "disqus" {
				opd:help "Disqus is a blog comment hosting service for websites and online communities";
				status obsolete;
			}

			enum "dns_crypt" {
				opd:help "The DNScrypt protocol is used to translate FQDN (Fully Qualified Domain Name) into address IP and vice versa with encrypted communication";
				status obsolete;
			}

			enum "epic_games" {
				opd:help "epic_games is an American video game and software development corporation";
				status obsolete;
			}

			enum "etisalat_c_me" {
				opd:help "C'Me, developed by Etisalat, is a mobile application offering voice and video calls along with instant messaging";
				status obsolete;
			}

			enum "fortnite" {
				opd:help "Fortnite is a game developed by Epic Games";
				status obsolete;
			}

			enum "foxnetworks" {
				opd:help "Fox Networks Group is a subsidiary of Fox Entertainment Group for television and cable";
				status obsolete;
			}

			enum "foxplus" {
				opd:help "Fox Plus is a streaming platform that lets people watch Fox Networks' group latest TV series, documentaries, Hollywood & Asian movies";
				status obsolete;
			}

			enum "google_news" {
				opd:help "Google News is a news aggregator and application developed by Google";
				status obsolete;
			}

			enum "grammarly" {
				opd:help "Grammarly is a cloud-based English-language writing-enhancement platform";
				status obsolete;
			}

			enum "gridftp" {
				opd:help "GridFTP is an extension to the FTP protocol for the grid computing platform Globus to allow peer-to-peer transfers of large files";
				status obsolete;
			}

			enum "hexatech" {
				opd:help "hexatech is a vpn to unblock anonymously any site or app";
				status obsolete;
			}

			enum "hike_messenger" {
				opd:help "Hike Messenger is an Indian instant messaging application";
				status obsolete;
			}

			enum "hot_vpn" {
				opd:help "Hot VPN is a free unlimited VPN proxy and WiFi security";
				status obsolete;
			}

			enum "hoxx_vpn" {
				opd:help "Hoxx VPN is an anonymizing web proxy";
				status obsolete;
			}

			enum "hpe_opagent" {
				opd:help "HPE Operation Agent is a standalone system management software, collecting metrics and applying configurations";
				status obsolete;
			}

			enum "hpe_opbridge" {
				opd:help "HPE Operation Bridge is a system and network management software for IT teams";
				status obsolete;
			}

			enum "hpe_sim" {
				opd:help "HPE Insight Manager is an inventory and health monitoring software for HP enterprise class hardware and has basic support for other vendors";
				status obsolete;
			}

			enum "hypers" {
				opd:help "HYPERS is a Chinese cloud platform";
				status obsolete;
			}

			enum "ibm" {
				opd:help "IBM (International Business Machines Corporation) is an American multinational technology company";
				status obsolete;
			}

			enum "iec104" {
				opd:help "IEC 60870-5-104 protocol (aka IEC 104) is a part of IEC Telecontrol Equipment and Systems Standard IEC 60870-5 that provides a communication profile for sending basic telecontrol messages between two systems in electrical engineering and power system automation";
				status obsolete;
			}

			enum "iflix" {
				opd:help "Iflix is a video streaming application based on the Akamai cloud service";
				status obsolete;
			}

			enum "ironsource" {
				opd:help "IronSource is a digital content company";
				status obsolete;
			}

			enum "jibe" {
				opd:help "Jibe is a job seeking messaging application implementing RCS (Rich Communication Services) distributed by google";
				status obsolete;
			}

			enum "jibe_cloud" {
				opd:help "Jibe cloud is a cloud SAAS services dedicated to social job seekers, and distributed by google";
				status obsolete;
			}

			enum "kafka" {
				opd:help "High throughput distributed messaging system";
				status obsolete;
			}

			enum "keku" {
				opd:help "KeKu provides virtual phone numbers to make and receive calls, send and receive SMS";
				status obsolete;
			}

			enum "kodi" {
				opd:help "Kodi (formerly XBox Media Center) is a free media player software application";
				status obsolete;
			}

			enum "libon" {
				opd:help "Libon is an application that provides international audio call feature";
				status obsolete;
			}

			enum "lifesize" {
				opd:help "Lifesize is a video and audio telecommunications company";
				status obsolete;
			}

			enum "line2_com" {
				opd:help "Line2 (formerly Toktumi) is a telecommunication company that provides a second phone number for USA or Canada";
				status obsolete;
			}

			enum "mf_ucmdb" {
				opd:help "Micro Focus Configuration Management System, previously known as HP Enterprise CMS, does the discovery and inventory of an IT infrastructure and its hosted services";
				status obsolete;
			}

			enum "modbus_rtu" {
				opd:help "Traffic related to Modbus Remote Terminal Unit (RTU), a distributed control system used in industrial process control (Emerson Process Management)";
				status obsolete;
			}

			enum "ms_ad_rms" {
				opd:help "Rights Management Service is a Microsoft rights management service for files and Office documents based on a central server linked to the Active Directory which acts like a DRM license server";
				status obsolete;
			}

			enum "mtalk" {
				opd:help "Mtalk is an instant messaging application that can provide a landline phone number";
				status obsolete;
			}

			enum "mumble" {
				opd:help "Mumble is an open source, low-latency, high quality voice chat software primarily intended for use while gaming";
				status obsolete;
			}

			enum "mytv_super" {
				opd:help "MyTV SUPER is an online video platform operated by TVB";
				status obsolete;
			}

			enum "opc_classic" {
				opd:help "OPC Classic is a specification based on Microsoft Windows technology, using COM/DCOM for communication among software components in a distributed client-server network";
				status obsolete;
			}

			enum "opera_turbo" {
				opd:help "Opera turbo is the protocol used for the Opera browser";
				status obsolete;
			}

			enum "optimicdn" {
				opd:help "OptimiCDN pilots multiple CDNs in an All-in-One Multi CDN service for optimized web performance & enhanced User Experience";
				status obsolete;
			}

			enum "oracle_oem" {
				opd:help "This module classifies the traffic generated by ORACLE OEM Management";
				status obsolete;
			}

			enum "oto_global" {
				opd:help "OTO Global is an instant messaging application that provides features to make landline or international calls";
				status obsolete;
			}

			enum "overwatch" {
				opd:help "Overwatch is an online video game part of Multiple First Person Shooter (Multi FPS) and described as hero shooter available on popular play stations";
				status obsolete;
			}

			enum "pacman" {
				opd:help "Pacman is the package manager of Arch Linux distribution";
				status obsolete;
			}

			enum "pccc" {
				opd:help "PCCC stands for \"Programmable Controller Communication Commands\". It is used to control software running in Programmable Logic Controller (PLC)";
				status obsolete;
			}

			enum "realvnc" {
				opd:help "RealVNC is a company that provides remote access software";
				status obsolete;
			}

			enum "ring_central" {
				opd:help "This plugin classifies website traffic of RingCentral, an application for video/audio conferencing";
				status obsolete;
			}

			enum "rockyou" {
				opd:help "RockYou is a full-service entertainment and media company";
				status obsolete;
			}

			enum "simpli_fi" {
				opd:help "Simpli.fi is an advertising technology company";
				status obsolete;
			}

			enum "smashcast" {
				opd:help "Smashcast is a gaming and eSports live streaming platform";
				status obsolete;
			}

			enum "snap_vpn" {
				opd:help "(Deprecated) SnapVPN is a free unlimited VPN proxy and WiFi security";
				status obsolete;
			}

			enum "splunk_cloud" {
				opd:help "Splunk Cloud is the data collection, indexing, and visualization service for operational intelligence";
				status obsolete;
			}

			enum "splunk_ufwd" {
				opd:help "Universal Forwarder is used to forward data Splunk application (6.5.0). It is designed to scale to large number of remote systems and collect a very large amount of data";
				status obsolete;
			}

			enum "springtech_vpn" {
				opd:help "This plugin classifies traffic relative to VPN applications distributed by SpringTech company, like Hot VPN, Turbo VPN, VPN Robot, Snap VPN, VPN Master Pro, VPN Monster, VPN Master";
				status obsolete;
			}

			enum "storebuff" {
				opd:help "Storebuff tests and analyzes network traffic from a given URL";
				status obsolete;
			}

			enum "symantec_sep" {
				opd:help "Symantec Endpoint Protection, developed by Symantec, is a security software suite, which consists of anti-malware, intrusion prevention and firewall features for servers and desktops";
				status obsolete;
			}

			enum "talkbox" {
				opd:help "TalkBox is a mobile group chat application from Hong Kong with support for voice messages";
				status obsolete;
			}

			enum "talkray" {
				opd:help "Talkray is an instant messaging application";
				status obsolete;
			}

			enum "tanium" {
				opd:help "This plugin classifies Tanium Client traffic";
				status obsolete;
			}

			enum "tenor" {
				opd:help "Tenor is a GIF search engine";
				status obsolete;
			}

			enum "textme" {
				opd:help "Text Me is an instant messaging application which can make texting and calling to any phone and make national & international calls";
				status obsolete;
			}

			enum "textplus" {
				opd:help "textPlus is an instant messaging application which can send and receive sms / text / MMS / group messages to anyone in the US or Canada";
				status obsolete;
			}

			enum "tiange_9158" {
				opd:help "Tiange 9158 is a social network that provides streaming and broadcast live video feature";
				status obsolete;
			}

			enum "tikl" {
				opd:help "Tikl is a simple VoIP push-to-talk communication application";
				status obsolete;
			}

			enum "tiktok" {
				opd:help "TikTok is a social network application acquired by ByteDance and previously known as Musical.ly";
				status obsolete;
			}

			enum "tribair" {
				opd:help "Tribair is an VoIP application for national and international audio calls";
				status obsolete;
			}

			enum "tunnelbear" {
				opd:help "TunnelBear VPN is a desktop application and browser extension that provides VPN";
				status obsolete;
			}

			enum "turbo_vpn" {
				opd:help "(Deprecated) Turbo vpn is an open source software application for android that implements virtual private network (VPN) techniques to connect using secure tunnels";
				status obsolete;
			}

			enum "tvb" {
				opd:help "Television Broadcasts Limited is a Hong Kong audio-visual group";
				status obsolete;
			}

			enum "ubisoft" {
				opd:help "Ubisoft is an online Game software editor and publisher (Far Cry, Assasin's Creed, Watchdogs etc)";
				status obsolete;
			}

			enum "unreal_engine" {
				opd:help "unreal_engine is a video game engine developed by Epic Games";
				status obsolete;
			}

			enum "upnp" {
				opd:help "UPnP, Universal Plug and Play, is a communication protocol designed to facilitate the exchange of information between different devices within a computer network";
				status obsolete;
			}

			enum "ventrilo" {
				opd:help "Ventrilo is a low-latency, encrypted voice chat software primarily intended for use while gaming";
				status obsolete;
			}

			enum "vonage_mobile" {
				opd:help "Vonage Mobile is an instant messaging application that provides features to make landline or international calls";
				status obsolete;
			}

			enum "voxer" {
				opd:help "Voxer is an instant messaging application that provides voice, text, photo, and video with walkie talkie messaging (Push-to-talk PTT) features in a secure messaging app";
				status obsolete;
			}

			enum "vpn1_com" {
				opd:help "Hoxx VPN is an anonymizing web proxy";
				status obsolete;
			}

			enum "vpn_master" {
				opd:help "VPN Master is a free and unlimited VPN tunnel";
				status obsolete;
			}

			enum "vpn_masterpro" {
				opd:help "VPN MasterPro is a free and unlimited VPN tunnel";
				status obsolete;
			}

			enum "vpn_monster" {
				opd:help "VPN Monster is a free and unlimited VPN tunnel";
				status obsolete;
			}

			enum "vpn_robot" {
				opd:help "VPN Robot is a free unlimited VPN proxy and WiFi security";
				status obsolete;
			}

			enum "vyke" {
				opd:help "Vyke is an IM allowing buying of phone numbers from countries such US, UK, Canada for VoIP, text messaging (SMS), and usual chat (File transfer/text)";
				status obsolete;
			}

			enum "x_vpn" {
				opd:help "x-vpn unblocks the web securely, privately and anonymously on your Android devices";
				status obsolete;
			}

			enum "youtube_music" {
				opd:help "YouTube Music is a music streaming app available for iOS and Android";
				status obsolete;
			}
		}
	}

	typedef relaxed-application-names {
		status obsolete;
		type enumeration {
			enum "8021ad" {
				opd:help "802.1AD is a protocol which allows sending VLAN membership information of a frame";
				status obsolete;
			}

			enum "8021q" {
				opd:help "802.1Q is a protocol which allows sending VLAN membership information of a frame";
				status obsolete;
			}

			enum "arp" {
				opd:help "The ARP protocol is used to determine the MAC Address of a PC for which the IP address is known";
				status obsolete;
			}

			enum "capwap" {
				opd:help "CAPWAP stands for Control And Provisioning of Wireless Access Points";
				status obsolete;
			}

			enum "cdp" {
				opd:help "Cisco Discovery Protocol (CDP) is a layer 2 protocol used by Cisco network equipment to discover other Cisco network equipment present on a link";
				status obsolete;
			}

			enum "eth" {
				opd:help "The Ethernet protocol enables the addressing and sending of data between stations of an Ethernet segment";
				status obsolete;
			}

			enum "etherip" {
				opd:help "The EtherIP protocol is used to encapsulate Ethernet frames in IP packets";
				status obsolete;
			}

			enum "garp" {
				opd:help "The Generic Attribute Registration Protocol (GARP) provides a generic framework whereby devices in a bridged LAN can register or delete attribute values between each other";
				status obsolete;
			}

			enum "gre" {
				opd:help "The Generic Routing Encapsulation protocol (GRE) is used to encapsulate a protocol into another one generically";
				status obsolete;
			}

			enum "gtp" {
				opd:help "The GPRS Tunneling Protocol (GTP) is used to create a tunnel between the SGSN and GGSNs of a mobile operator network, thus allowing mobile station data to be transmitted";
				status obsolete;
			}

			enum "icmp" {
				opd:help "The Internet Control Message protocol (ICMP) is the diagnostic protocol of IPv4 networks";
				status obsolete;
			}

			enum "ip" {
				opd:help "The Internet Protocol allows logical addressing of stations over an interconnected system of networks";
				status obsolete;
			}

			enum "ip6" {
				opd:help "IPv6 is the next generation protocol designed by the IETF to replace the current version Internet Protocol, IP Version 4 (IPv4)";
				status obsolete;
			}

			enum "ipx" {
				opd:help "Internet Protocol Exchange (IPX) is Novell's network layer 3 protocol";
				status obsolete;
			}

			enum "l2tp" {
				opd:help "Layer Two Tunneling Protocol (L2TP) is an extension of the Point-to-Point Tunneling Protocol (PPTP) used by an Internet service provider (ISP) to enable the operation of a virtual private network (VPN) over the Internet";
				status obsolete;
			}

			enum "llc" {
				opd:help "The IEEE 802.2 Logical Link Control (LLC) protocol provides a link mechanism for upper layer protocols encapsulated in a frame";
				status obsolete;
			}

			enum "mobile_ip" {
				opd:help "Mobile IP is an IETF standard communications protocol that is designed to allow mobile device users to move from one network to another while maintaining a permanent IP address";
				status obsolete;
			}

			enum "mpls" {
				opd:help "Multiprotocol Label Switching (MPLS) is an Internet Engineering Task Force (IETF) protocol";
				status obsolete;
			}

			enum "netbios" {
				opd:help "NetBIOS defines a software interface and standard methods providing a communication interface between the application program and the attached medium";
				status obsolete;
			}

			enum "pp" {
				opd:help "ISO 8823/X.226 OSI PRESENTATION PROTOCOL (PP)";
				status obsolete;
			}

			enum "ppp" {
				opd:help "PPP (Point-to-Point Protocol) is a link layer protocol used for transferring data along a Point to Point link";
				status obsolete;
			}

			enum "pppoe" {
				opd:help "PPP over Ethernet (PPPoE) provides the ability to connect a network of hosts over a simple bridging access device to a remote Access Concentrator";
				status obsolete;
			}

			enum "pwe" {
				opd:help "Pseudo Wire Emulation (PWE) is a protocol for traffic encapsulation";
				status obsolete;
			}

			enum "sctp" {
				opd:help "SCTP (Stream Control Transmission Protocol) is a protocol designed to transport PSTN signaling messages over IP networks";
				status obsolete;
			}

			enum "snap" {
				opd:help "Sub-Network Access Protocol (SNAP) is a protocol encapsulated in the LLC protocol enabling the encapsulation of a greater number of protocols in Ethernet II frames";
				status obsolete;
			}

			enum "stp" {
				opd:help "Spanning Tree Protocol allows the use of layer 2 networks with redundant paths by creating a covering tree on which frames will be transmitted";
				status obsolete;
			}

			enum "tcp" {
				opd:help "TCP is a protocol providing a connection-oriented and reliable transfer service";
				status obsolete;
			}

			enum "udp" {
				opd:help "The User Datagram Protocol is a transport protocol providing a simple but non-reliable message transfer service in IP networks";
				status obsolete;
			}

			enum "vxlan" {
				opd:help "vxlan is a network virtualization technology that uses vlan-like encapsulation over udp";
				status obsolete;
			}
		}
	}
}
