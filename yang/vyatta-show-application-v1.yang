module vyatta-show-application-v1 {
	namespace "urn:vyatta.com:mgmt:vyatta-show-application:1";
	prefix vyatta-show-application-v1;

	import vyatta-opd-extensions-v1 {
		prefix opd;
	}

	import vyatta-op-show-v1 {
		prefix show;
	}

	import vyatta-dpi-application-names-v1 {
		prefix app-names;
	}

	import vyatta-dpi-application-types-v1 {
		prefix app-types;
	}

	organization "AT&T Inc.";
	contact	"AT&T
		 Postal: 208 S. Akard Street
		         Dallas, TX 75202, USA
		 Web: www.att.com";

	description
		"Copyright (c) 2017-2020 AT&T Intellectual Property
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 Defines 'show application' operational CLI";

	revision 2020-05-12 {
		description "Corrected contact address.
			     Added BSD-3-Clause license.
			     Added DPI engine node;
			     obsoleted name and type.
			     Obsoleted 'show application info'.";
	}

	revision 2018-08-17 {
		description "Correct info node to opd:command
			     since it doesn't take an argument.";
	}
	revision 2017-09-01 {
		description "Initial version";
	}

	opd:augment /show:show {
		opd:command application {
			opd:help "Show Deep Packet Inspection (DPI) application information";

			opd:option name {
				status obsolete;
				opd:help "Show DPI application name information";
				opd:on-enter 'opc -field $4 -op=helpforfield show application name';
				type app-names:application-names;
			}

			opd:option type {
				status obsolete;
				opd:help "Show DPI application type information";
				opd:on-enter 'opc -field $4 -op=helpforfield show application type';
				type app-types:application-types;
			}

			opd:command info {
				status obsolete;
				opd:help "Show DPI application information";
			}

			opd:command engine {
				opd:help "Show DPI engine information";
			}
		}
	}
}
