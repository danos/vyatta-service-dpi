module vyatta-resource-group-application-v1 {
	namespace "urn:vyatta.com:mgmt:vyatta-resource-group-application:1";
	prefix vyatta-resource-group-application-v1;

	import configd-v1 {
		prefix configd;
	}
	import vyatta-resources-group-v1 {
		prefix groups;
	}
	import vyatta-resources-v1 {
		prefix resources;
	}
	import vyatta-fw-types-v1 {
		prefix fw-types;
	}

	organization "AT&T Inc.";
	contact "AT&T
		 Postal: 208 S. Akard Street
		         Dallas, TX 75202, USA
		 Web: www.att.com";

	description
		"Copyright (c) 2020-2021 AT&T Intellectual Property
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for application resource groups.";

	revision 2021-06-02 {
		description "Call end-app-res-grps just once";
	}

	revision 2020-08-06 {
		description "Initial revision";
	}

	grouping app-group {
		leaf group {
			description  "Match a user-defined application group";
			configd:help "Match a user-defined application group";
			type leafref {
				path "/resources:resources/groups:group/" +
					 "vyatta-resource-group-application-v1:application-group/" +
					 "vyatta-resource-group-application-v1:group-name";
			}
		}
	}

	augment "/resources:resources/groups:group" {
		configd:end "end-app-res-grps";
		list application-group {
			description  "Group of applications";
			configd:help "Group of applications";
			key "group-name";
			leaf group-name {
				type fw-types:group-name;
				description  "Group of applications";
				configd:help "Group of applications";
			}
			leaf description {
				type string;
				description  "Application group description";
				configd:help "Application group description";
			}
			container engine {
				description  "Add an application by engine";
				configd:help "Add an application by engine";
			}
		}
	}
}
