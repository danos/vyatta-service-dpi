module vyatta-ndpi-v1 {
	namespace "urn:vyatta.com:mgmt:vyatta-ndpi:1";
	prefix vyatta-ndpi-v1;

	import configd-v1 {
		prefix configd;
	}
	import vyatta-security-v1 {
		prefix security;
	}
	import vyatta-security-application-v1 {
		prefix security-app;
	}
	import vyatta-ndpi-application-names-v1 {
		prefix ndpi-app-names;
	}
	import vyatta-ndpi-application-types-v1 {
		prefix ndpi-app-types;
	}
	import vyatta-resources-v1 {
		prefix resources;
	}
	import vyatta-resources-group-v1 {
		prefix groups;
	}
	import vyatta-resource-group-application-v1 {
		prefix res-grp-app;
	}

	organization "AT&T Inc.";
	contact "AT&T
		 Postal: 208 S. Akard Street
		         Dallas, TX 75202, USA
		 Web: www.att.com";

	description
		"Copyright (c) 2020, AT&T Intellectual Property
		 All rights reserved.

		 Redistribution and use in source and binary forms,
		 with or without modification, are permitted provided
		 that the following conditions are met:

		 1. Redistributions of source code must retain the
		    above copyright notice, this list of conditions and
		    the following disclaimer.
		 2. Redistributions in binary form must reproduce
		    the above copyright notice, this list of conditions
		    and the following disclaimer in the documentation
		    and/or other materials provided with the distribution.
		 3. Neither the name of the copyright holder nor the
		    names of its contributors may be used to endorse or
		    promote products derived from this software without
		    specific prior written permission.

		 THIS SOFTWARE IS PROVIDED BY THE COPYRIGHT HOLDERS
		 AND CONTRIBUTORS 'AS IS' AND ANY EXPRESS OR IMPLIED
		 WARRANTIES, INCLUDING, BUT NOT LIMITED TO, THE IMPLIED
		 WARRANTIES OF MERCHANTABILITY AND FITNESS FOR A
		 PARTICULAR PURPOSE ARE DISCLAIMED. IN NO EVENT SHALL
		 THE COPYRIGHT HOLDER OR CONTRIBUTORS BE LIABLE FOR
		 ANY DIRECT, INDIRECT, INCIDENTAL, SPECIAL, EXEMPLARY,
		 OR CONSEQUENTIAL DAMAGES (INCLUDING, BUT NOT LIMITED
		 TO, PROCUREMENT OF SUBSTITUTE GOODS OR SERVICES; LOSS
		 OF USE, DATA, OR PROFITS; OR BUSINESS INTERRUPTION)
		 HOWEVER CAUSED AND ON ANY THEORY OF LIABILITY, WHETHER
		 IN CONTRACT, STRICT LIABILITY, OR TORT (INCLUDING
		 NEGLIGENCE OR OTHERWISE) ARISING IN ANY WAY OUT OF THE
		 USE OF THIS SOFTWARE, EVEN IF ADVISED OF THE POSSIBILITY
		 OF SUCH DAMAGE.

		 SPDX-License-Identifier: BSD-3-Clause

		 YANG module for nDPI.
		 Adds engine nodes to QoS, PBR, Firewall and App-Firewall.";

	revision 2020-08-20 {
		description "Initial revision";
	}

	grouping ndpi-application-name {
		leaf name {
			description  "Specify an nDPI application name";
			configd:help "Specify an nDPI application name";
			type ndpi-app-names:application-names;
		}
	}

	grouping ndpi-application-type {
		leaf type {
			description  "Specify an nDPI application type";
			configd:help "Specify an nDPI application type";
			type ndpi-app-types:application-types;
		}
	}

	grouping ndpi-application-protocol {
		leaf protocol {
			description  "Specify an nDPI application protocol";
			configd:help "Specify an nDPI application protocol";
			type ndpi-app-names:application-names;
		}
	}

	augment "/security:security/security-app:application/" +
		"security-app:firewall/security-app:name/security-app:rule/" +
		"security-app:engine" {
		description "Add nDPI functionality to security application";
		container ndpi {
			description  "Use the nDPI application engine";
			configd:help "Use the nDPI application engine";
			presence "nDPI application rule configuration";
			must "count(name|type|protocol) = 1" {
				error-message "Specify exactly one of 'name', 'type', or 'protocol'";
			}
			uses ndpi-application-name;
			uses ndpi-application-type;
			uses ndpi-application-protocol;
		}
	}

	augment "/resources:resources/groups:group/" +
		"res-grp-app:application-group/res-grp-app:engine" {
		description "Add nDPI functionality to resource groups";
		container ndpi {
			description  "Use the nDPI application engine";
			configd:help "Use the nDPI application engine";
			list name {
				description  "Specify an nDPI application name";
				configd:help "Specify an nDPI application name";
				key "name";
				uses ndpi-application-name;
			}
			list type {
				description  "Specify an nDPI application type";
				configd:help "Specify an nDPI application type";
				key "type";
				uses ndpi-application-type;
			}
			list protocol {
				description  "Specify an nDPI application protocol";
				configd:help "Specify an nDPI application protocol";
				key "protocol";
				uses ndpi-application-protocol;
			}
		}
	}
}
